submodule infix-if {
  yang-version 1.1;
  belongs-to infix {
    prefix ix;
  }

  include infix-native;

  typedef interface-ref {
    type leafref {
      path "/native/interfaces/interface/name";
    }
    description
      "This type is used by data models that need to reference
       interfaces.";
  }

  augment "/native" {
    container interfaces {
      list interface {
        key "name";

	leaf name {
	  type string;
	}

	choice type;
	choice port;
      }
    }
  }
}
