module device {
    yang-version 1.1;
    namespace "urn:kernelkit:yang:device";
    prefix device;

    import ietf-datastores {
        prefix ds;
    }

    import ietf-system {
        prefix sys;
    }

    import infix {
        prefix ix;
    }

    import clixon-autocli {
        prefix autocli;
    }

    description
        "Base model
         ";

    revision 2023-02-10 {
      description
	"Initial revision.";
      reference
	"N/A";
    }
}
