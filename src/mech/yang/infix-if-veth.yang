submodule infix-if-veth {
  yang-version 1.1;
  belongs-to infix {
    prefix ix;
  }

  include infix-if;

  augment "/native/interfaces/interface/type" {
    case veth {
      container veth {
        description
          "Virtual ethernet pair specific configuration";

        leaf peer {
          type interface-ref;
          mandatory true;
          description
            "Peer veth interface to which this interface is connected";
        }
      }
    }
  }
}
