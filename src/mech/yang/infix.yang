module infix {
  yang-version 1.1;
  namespace "urn:kernelkit:yang:infix";
  prefix ix;

  include infix-native;
  include infix-if;
  include infix-if-bridge;
  include infix-if-lag;
  include infix-if-veth;
  include infix-if-vlan;

  organization "Kernelkit";
  contact
    "https://github.com/kernelkit/";
  description
    "Infix's native system model";

  revision 2023-03-17 {
    description
      "Initial revision.";
    reference
      "github.com/kernelkit/infix";
  }
}
