module infix-meta {
  yang-version 1.1;
  namespace "urn:infix:meta:ns:yang:1.0";
  prefix infix-meta;

  organization "KernelKit";
  contact      "kernelkit@googlegroups.com";
  description  "Infix metadata.";

  revision 2024-06-19 {
    description "Initial revision.";
    reference "internal";
  }

  container meta {
    leaf version {
      status obsolete; // Ensure frontends don't show this, used for migration.
      description "Configuration file format version, automatically generated.";
      type string;
    }
  }
}
