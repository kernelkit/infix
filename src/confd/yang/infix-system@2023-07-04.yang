module infix-system {
  yang-version 1.1;
  namespace "urn:infix:system:ns:yang:1.0";
  prefix infix-sys;

  import ietf-system {
    prefix sys;
  }
  import iana-timezones {
    prefix iana-tz;
  }
  include infix-system-software;

  organization "KernelKit";
  contact      "kernelkit@googlegroups.com";
  description  "Infix augments and deviations to ietf-system.";

  revision 2023-07-04 {
    description "Updating/adding deviation specifications:
                 - timezone-name (use tz defs from iana-timezone.yang)
                 - timezone-utc-offset (updated path for 'not-supported')
                 - radius ('not-supported')
                 - dns-resolver port ('not-supported')
                 - authentication username (limit length and pattern)";
    reference "internal";
  }

  revision 2023-04-11 {
    description "Initial revision.";
    reference "internal";
  }

  typedef username {
    type string {
      length "1..256";
      pattern "[_a-zA-Z0-9][-._a-zA-Z0-9]*$?";
    }
  }

  augment "/sys:system" {
    description "Augments to ietf-system not found in any other model.";
    leaf motd {
      type string;
      description "Set the MotD (Message of the Day), shown after login";
    }
  }

  deviation "/sys:system/sys:clock/sys:timezone/sys:timezone-name/sys:timezone-name" {
    deviate replace {
      type iana-tz:iana-timezone;
    }
  }

  deviation "/sys:system/sys:clock/sys:timezone/sys:timezone-utc-offset" {
    deviate not-supported;
  }

  deviation "/sys:system/sys:radius" {
    deviate not-supported;
  }

  deviation "/sys:system/sys:dns-resolver/sys:server/sys:transport/sys:udp-and-tcp/sys:udp-and-tcp/sys:port" {
    deviate not-supported;
  }

  deviation "/sys:system/sys:authentication/sys:user/sys:name" {
    deviate replace {
      type infix-sys:username;
    }
  }
}
