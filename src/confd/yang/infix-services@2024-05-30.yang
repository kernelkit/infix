module infix-services {
  yang-version 1.1;
  namespace "urn:ietf:params:xml:ns:yang:infix-services";
  prefix infix-svc;

  organization "KernelKit";
  contact      "kernelkit@googlegroups.com";
  description  "Infix services, generic.";

  revision 2024-05-30 {
    description "Add support for RESTCONF enable/disable as a web service.";
    reference "internal";
  }
  revision 2024-04-08 {
    description "Initial support for web services.";
    reference "internal";
  }
  revision 2023-10-16 {
    description "Drop SSDP support, mDNS-SD is now available in Windows 10.";
    reference "internal";
  }
  revision 2023-08-22 {
    description "Initial revision, add SSDP and mDNS-SD enable/disable only.";
    reference "internal";
  }

  /*
   * Data nodes
   */

  container mdns {
    description "Advertise system and services over mDNS-SD, IPv4 and IPv6.";

    leaf enabled {
      description "Globally enable or disable mDNS/SD on all interfaces.";
      type boolean;
    }
  }

  container web {
    description "Web services";

    leaf enabled {
      description "Enable or disable on all web services.

                   Enabling this setting activates a web proxy server reponsible
                   for routing requests to other web applications, as well as it
                   redirecting all insecure HTTP requests to HTTPS.

                   Disabling this setting disables the web proxy server and all
                   other services/applications that run behind it.";
      type boolean;
    }

    container console {
      description "Web console interface.";

      leaf enabled {
        description "Enable or disable web console interface on port 7681.";
        type boolean;
      }
    }

    container netbrowse {
      description "mDNS Network Browser.";

      leaf enabled {
        description "Enable or disable mDNS Network Browser at https://network.local.";
        type boolean;
      }
    }

    container restconf {
      description "IETF RESTCONF Server.";

      leaf enabled {
        description "Enable or disable https://device.local/resconf API endpoint.";
        type boolean;
      }
    }
  }
}
