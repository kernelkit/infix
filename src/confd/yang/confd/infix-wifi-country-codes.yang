module infix-wifi-country-codes {
  yang-version 1.1;
  namespace "urn:infix:wifi-country-codes:ns:yang:1.0";
  prefix iwcc;

  organization   "KernelKit";

  contact        "kernelkit@googlegroups.com";

  description
    "Country codes for the Wi-Fi regulatory domain, ISO 3166-1 alpha-2,
     limited to the countries the Linux wireless regulatory database
     has rules for.";

  revision 2026-10-06 {
    description
      "Limit the list to the countries the Linux regulatory database has
       rules for, a code without rules is silently ignored by the kernel
       and leaves the radios in the world domain.";
    reference
      "wireless-regdb 2026.09.03";
  }

  revision 2025-11-28 {
    description
      "Add support for 00 - World regulatory domain.";
    reference
      "Internal";
  }

  revision 2025-06-02 {
    description
      "Initial revision for WiFi country code support.";
    reference
      "ISO 3166-1:2020 Codes for the representation of names of countries
       and their subdivisions -- Part 1: Country codes";
  }

  typedef country-code {
    type enumeration {
      enum "00" { description "World regulatory domain, the most restrictive one: no 6 GHz, listen-only on 5 GHz, no access point"; }
      enum "AD" { description "Andorra"; }
      enum "AE" { description "United Arab Emirates"; }
      enum "AF" { description "Afghanistan"; }
      enum "AI" { description "Anguilla"; }
      enum "AL" { description "Albania"; }
      enum "AM" { description "Armenia"; }
      enum "AR" { description "Argentina"; }
      enum "AS" { description "American Samoa"; }
      enum "AT" { description "Austria"; }
      enum "AU" { description "Australia"; }
      enum "AW" { description "Aruba"; }
      enum "AZ" { description "Azerbaijan"; }
      enum "BA" { description "Bosnia and Herzegovina"; }
      enum "BB" { description "Barbados"; }
      enum "BD" { description "Bangladesh"; }
      enum "BE" { description "Belgium"; }
      enum "BF" { description "Burkina Faso"; }
      enum "BG" { description "Bulgaria"; }
      enum "BH" { description "Bahrain"; }
      enum "BL" { description "Saint Barthélemy"; }
      enum "BM" { description "Bermuda"; }
      enum "BN" { description "Brunei Darussalam"; }
      enum "BO" { description "Bolivia"; }
      enum "BR" { description "Brazil"; }
      enum "BS" { description "Bahamas"; }
      enum "BT" { description "Bhutan"; }
      enum "BW" { description "Botswana"; }
      enum "BY" { description "Belarus"; }
      enum "BZ" { description "Belize"; }
      enum "CA" { description "Canada"; }
      enum "CF" { description "Central African Republic"; }
      enum "CH" { description "Switzerland"; }
      enum "CI" { description "Côte d'Ivoire"; }
      enum "CL" { description "Chile"; }
      enum "CN" { description "China"; }
      enum "CO" { description "Colombia"; }
      enum "CR" { description "Costa Rica"; }
      enum "CU" { description "Cuba"; }
      enum "CX" { description "Christmas Island"; }
      enum "CY" { description "Cyprus"; }
      enum "CZ" { description "Czechia"; }
      enum "DE" { description "Germany"; }
      enum "DK" { description "Denmark"; }
      enum "DM" { description "Dominica"; }
      enum "DO" { description "Dominican Republic"; }
      enum "DZ" { description "Algeria"; }
      enum "EC" { description "Ecuador"; }
      enum "EE" { description "Estonia"; }
      enum "EG" { description "Egypt"; }
      enum "ES" { description "Spain"; }
      enum "ET" { description "Ethiopia"; }
      enum "FI" { description "Finland"; }
      enum "FM" { description "Micronesia"; }
      enum "FO" { description "Faroe Islands"; }
      enum "FR" { description "France"; }
      enum "GB" { description "United Kingdom"; }
      enum "GD" { description "Grenada"; }
      enum "GE" { description "Georgia"; }
      enum "GF" { description "French Guiana"; }
      enum "GH" { description "Ghana"; }
      enum "GI" { description "Gibraltar"; }
      enum "GL" { description "Greenland"; }
      enum "GP" { description "Guadeloupe"; }
      enum "GR" { description "Greece"; }
      enum "GT" { description "Guatemala"; }
      enum "GU" { description "Guam"; }
      enum "GY" { description "Guyana"; }
      enum "HK" { description "Hong Kong"; }
      enum "HN" { description "Honduras"; }
      enum "HR" { description "Croatia"; }
      enum "HT" { description "Haiti"; }
      enum "HU" { description "Hungary"; }
      enum "ID" { description "Indonesia"; }
      enum "IE" { description "Ireland"; }
      enum "IL" { description "Israel"; }
      enum "IM" { description "Isle of Man"; }
      enum "IN" { description "India"; }
      enum "IR" { description "Iran"; }
      enum "IS" { description "Iceland"; }
      enum "IT" { description "Italy"; }
      enum "JM" { description "Jamaica"; }
      enum "JO" { description "Jordan"; }
      enum "JP" { description "Japan"; }
      enum "KE" { description "Kenya"; }
      enum "KH" { description "Cambodia"; }
      enum "KN" { description "Saint Kitts and Nevis"; }
      enum "KP" { description "Korea, Democratic People's Republic of"; }
      enum "KR" { description "Korea, Republic of"; }
      enum "KW" { description "Kuwait"; }
      enum "KY" { description "Cayman Islands"; }
      enum "KZ" { description "Kazakhstan"; }
      enum "LB" { description "Lebanon"; }
      enum "LC" { description "Saint Lucia"; }
      enum "LI" { description "Liechtenstein"; }
      enum "LK" { description "Sri Lanka"; }
      enum "LS" { description "Lesotho"; }
      enum "LT" { description "Lithuania"; }
      enum "LU" { description "Luxembourg"; }
      enum "LV" { description "Latvia"; }
      enum "MA" { description "Morocco"; }
      enum "MC" { description "Monaco"; }
      enum "MD" { description "Moldova"; }
      enum "ME" { description "Montenegro"; }
      enum "MF" { description "Saint Martin (French part)"; }
      enum "MH" { description "Marshall Islands"; }
      enum "MK" { description "North Macedonia"; }
      enum "MN" { description "Mongolia"; }
      enum "MO" { description "Macao"; }
      enum "MP" { description "Northern Mariana Islands"; }
      enum "MQ" { description "Martinique"; }
      enum "MR" { description "Mauritania"; }
      enum "MT" { description "Malta"; }
      enum "MU" { description "Mauritius"; }
      enum "MV" { description "Maldives"; }
      enum "MW" { description "Malawi"; }
      enum "MX" { description "Mexico"; }
      enum "MY" { description "Malaysia"; }
      enum "NA" { description "Namibia"; }
      enum "NG" { description "Nigeria"; }
      enum "NI" { description "Nicaragua"; }
      enum "NL" { description "Netherlands"; }
      enum "NO" { description "Norway"; }
      enum "NP" { description "Nepal"; }
      enum "NZ" { description "New Zealand"; }
      enum "OM" { description "Oman"; }
      enum "PA" { description "Panama"; }
      enum "PE" { description "Peru"; }
      enum "PF" { description "French Polynesia"; }
      enum "PG" { description "Papua New Guinea"; }
      enum "PH" { description "Philippines"; }
      enum "PK" { description "Pakistan"; }
      enum "PL" { description "Poland"; }
      enum "PM" { description "Saint Pierre and Miquelon"; }
      enum "PR" { description "Puerto Rico"; }
      enum "PT" { description "Portugal"; }
      enum "PW" { description "Palau"; }
      enum "PY" { description "Paraguay"; }
      enum "QA" { description "Qatar"; }
      enum "RE" { description "Réunion"; }
      enum "RO" { description "Romania"; }
      enum "RS" { description "Serbia"; }
      enum "RU" { description "Russian Federation"; }
      enum "RW" { description "Rwanda"; }
      enum "SA" { description "Saudi Arabia"; }
      enum "SE" { description "Sweden"; }
      enum "SG" { description "Singapore"; }
      enum "SI" { description "Slovenia"; }
      enum "SK" { description "Slovakia"; }
      enum "SM" { description "San Marino"; }
      enum "SN" { description "Senegal"; }
      enum "SR" { description "Suriname"; }
      enum "SV" { description "El Salvador"; }
      enum "SX" { description "Sint Maarten (Dutch part)"; }
      enum "SY" { description "Syrian Arab Republic"; }
      enum "TC" { description "Turks and Caicos Islands"; }
      enum "TD" { description "Chad"; }
      enum "TG" { description "Togo"; }
      enum "TH" { description "Thailand"; }
      enum "TN" { description "Tunisia"; }
      enum "TR" { description "Turkey"; }
      enum "TT" { description "Trinidad and Tobago"; }
      enum "TW" { description "Taiwan"; }
      enum "TZ" { description "Tanzania"; }
      enum "UA" { description "Ukraine"; }
      enum "UG" { description "Uganda"; }
      enum "US" { description "United States of America"; }
      enum "UY" { description "Uruguay"; }
      enum "UZ" { description "Uzbekistan"; }
      enum "VA" { description "Holy See (Vatican City State)"; }
      enum "VC" { description "Saint Vincent and the Grenadines"; }
      enum "VE" { description "Venezuela"; }
      enum "VI" { description "Virgin Islands, U.S."; }
      enum "VN" { description "Viet Nam"; }
      enum "VU" { description "Vanuatu"; }
      enum "WF" { description "Wallis and Futuna"; }
      enum "WS" { description "Samoa"; }
      enum "YE" { description "Yemen"; }
      enum "YT" { description "Mayotte"; }
      enum "ZA" { description "South Africa"; }
      enum "ZW" { description "Zimbabwe"; }
    }
    description
      "ISO 3166-1 alpha-2 country codes for the Wi-Fi regulatory domain,
       limited to the countries the Linux wireless regulatory database
       has rules for, plus '00' for the world domain.";
    reference
      "ISO 3166-1:2020 Codes for the representation of names of countries
       and their subdivisions -- Part 1: Country codes
       https://git.kernel.org/pub/scm/linux/kernel/git/wens/wireless-regdb.git";
  }
}
