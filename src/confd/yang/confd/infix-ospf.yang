module infix-ospf {
  yang-version 1.1;
  namespace "urn:infix:ospf:ns:yang:1.0";
  prefix infix-ospf;

  import ietf-routing {
    prefix rt;
  }
  import ietf-ospf {
    prefix ospf;
  }
  import ietf-inet-types {
    prefix inet;
  }
  import ietf-interfaces {
    prefix if;
  }
  import infix-routing {
    prefix infix-rt;
  }

  organization "KernelKit";
  contact      "kernelkit@googlegroups.com";
  description  "Deviations and augments for ietf-ospf.";

  revision 2026-10-30 {
    description "The local RIB is no longer operational data, the new
                 get-routes action reads it from the daemon on request.";
    reference "internal";
  }

  revision 2026-10-26 {
    description "Initial revision, the ietf-ospf deviations and augments from
                 infix-routing.";
    reference "internal";
  }

  /* show routes */
  deviation "/rt:routing/rt:ribs/rt:rib/rt:routes/rt:route/ospf:tag" {
    deviate not-supported;
  }
  deviation "/rt:routing/rt:ribs/rt:rib/rt:routes/rt:route/ospf:route-type" {
    deviate not-supported;
  }

  /* OSPF */


/*
  deviation "/rt:routing/rt:control-plane-protocols/rt:control-plane-protocol/rt:type" {
    deviate add {
      must "derived-from-or-self(., 'ospf:ospfv2') or "+
           "derived-from-or-self(., 'rt:static')" {
          description "Only OSPFv2 and Static routes are supported in Infix.";
        }
    }
  }
*/
  augment "/rt:routing/rt:control-plane-protocols/rt:control-plane-protocol/ospf:ospf" {
    description "ietf-ospf lack the setting to generate a default route";
    container default-route-advertise {
      description "Distribute default route to network";
      leaf enable {
        status obsolete;
        description "Legacy, replaced by 'enabled'.";
        type boolean;
      }
      leaf enabled {
        description "Distribute default route";
        type boolean;
      }
      leaf always {
        description "Always distribute default route, even if no local default route exist.
                     If set to false, a default route will only be distributed if a default route exist
                     in the local routing table.";
        type boolean;
      }
    }
  }
  augment "/rt:routing/rt:control-plane-protocols/rt:control-plane-protocol/ospf:ospf" {
    description "ietf-ospf does not contain redistribution
                 7. How should route redistribution be configured? I see ietf-rip.yang has a separate
                 container for that purpose, but ietf-ospf.yang (and other IGP modules) don't do the
                 same. I also noticed the BGP model is using definition from ietf-routing-policy.yang.

                 Different vendors handle redistribution in different ways. This could be added with
                 an augmentation if there were agreement.

                 https://marc.info/?l=ms-ospf&m=166258444409552&w=2";
    container redistribute {
      list redistribute {
        key "protocol";
        description "Redistribute protocols into OSPF";
        must "not(derived-from-or-self(../../../rt:type, 'infix-rt:ospfv3')) or "
           + "protocol != 'ospf'" {
          error-message "OSPFv3 cannot redistribute OSPF routes, OSPFv2 routes
                         are IPv4 only.";
        }
        leaf protocol {
          type infix-rt:infix-distribute-protocol;
          description "Set protocol to redistribute";
        }
      }
    }
  }
  augment "/rt:routing/rt:control-plane-protocols/rt:control-plane-protocol/ospf:ospf" {
    description "Add support for configurable OSPF debug logging.
                 Allows users to enable specific OSPF debug categories for troubleshooting.
                 All debug options default to disabled to prevent log flooding in
                 production environments.";
    container debug {
      description "OSPF debug logging configuration";
      leaf bfd {
        type boolean;
        default false;
        description "Enable OSPF BFD (Bidirectional Forwarding Detection) debug messages";
      }
      leaf packet {
        type boolean;
        default false;
        description "Enable detailed OSPF packet debug messages (all packet types)";
      }
      leaf ism {
        type boolean;
        default false;
        description "Enable OSPF Interface State Machine debug messages";
      }
      leaf nsm {
        type boolean;
        default false;
        description "Enable OSPF Neighbor State Machine debug messages";
      }
      leaf default-information {
        type boolean;
        default false;
        description "Enable OSPF default route origination debug messages";
      }
      leaf nssa {
        type boolean;
        default false;
        description "Enable OSPF NSSA (Not-So-Stubby Area) debug messages";
      }
    }
  }
  deviation "/rt:routing/rt:control-plane-protocols/rt:control-plane-protocol/ospf:ospf/ospf:areas/ospf:area/ospf:interfaces/ospf:interface" {
    deviate add {
      must "count(../../../../ospf:areas/ospf:area/ospf:interfaces/ospf:interface[ospf:name=current()/name]) <= 1" {
        error-message "Only one area per interface is allowed.";
      }
    }
  }

  deviation "/rt:routing/rt:control-plane-protocols/rt:control-plane-protocol/ospf:ospf" {
    deviate add {
      must "not(derived-from-or-self(../rt:type, 'infix-rt:ospfv3')) or "
         + "ospf:explicit-router-id" {
        error-message "OSPFv3 requires an explicit-router-id.";
      }
    }
  }

  /* The reference bandwidth must be the same on all routers in the OSPF
     domain.  Frr always derives the interface cost from it, unless a cost
     is set on the interface, so auto-cost can not be disabled. */
  deviation "/rt:routing/rt:control-plane-protocols/rt:control-plane-protocol/ospf:ospf/ospf:auto-cost/ospf:enabled" {
    deviate add {
      default "true";
      must ". = 'true'" {
        error-message "Disabling OSPF auto-cost is not supported.";
      }
    }
  }
  deviation "/rt:routing/rt:control-plane-protocols/rt:control-plane-protocol/ospf:ospf/ospf:auto-cost/ospf:reference-bandwidth" {
    deviate add {
      default "100000";
    }
  }
  deviation "/rt:routing/rt:control-plane-protocols/rt:control-plane-protocol/ospf:ospf/ospf:database" {
    deviate not-supported;
  }
  deviation "/rt:routing/rt:control-plane-protocols/rt:control-plane-protocol/ospf:ospf/ospf:graceful-restart" {
    deviate not-supported;
  }
  deviation "/rt:routing/rt:control-plane-protocols/rt:control-plane-protocol/ospf:ospf/ospf:enabled" {
    deviate not-supported;
  }

  deviation "/rt:routing/rt:control-plane-protocols/rt:control-plane-protocol/ospf:ospf/ospf:spf-control" {
    deviate not-supported;
  }

  /* FRR ospf6d carries IPv6 routes only; IPv4-over-OSPFv3 (RFC 5838) is not
     supported.  OSPFv2 vs OSPFv3 is selected by the control-plane-protocol
     type, so the address-family leaf is omitted. */
  deviation "/rt:routing/rt:control-plane-protocols/rt:control-plane-protocol/ospf:ospf/ospf:address-family" {
    deviate not-supported;
  }

  deviation "/rt:routing/rt:control-plane-protocols/rt:control-plane-protocol/ospf:ospf/ospf:preference" {
    deviate not-supported;
  }
  deviation "/rt:routing/rt:control-plane-protocols/rt:control-plane-protocol/ospf:ospf/ospf:stub-router" {
    deviate not-supported;
  }
  deviation "/rt:routing/rt:control-plane-protocols/rt:control-plane-protocol/ospf:ospf/ospf:topologies" {
    deviate not-supported;
  }
  deviation "/rt:routing/rt:control-plane-protocols/rt:control-plane-protocol/ospf:ospf/ospf:statistics" {
    deviate not-supported;
  }
  deviation "/rt:routing/rt:control-plane-protocols/rt:control-plane-protocol/ospf:ospf/ospf:database-control" {
    deviate not-supported;
  }
  deviation "/rt:routing/rt:control-plane-protocols/rt:control-plane-protocol/ospf:ospf/ospf:lsa-log" {
    deviate not-supported;
  }
  deviation "/rt:routing/rt:control-plane-protocols/rt:control-plane-protocol/ospf:ospf/ospf:spf-log" {
    deviate not-supported;
  }
  deviation "/rt:routing/rt:control-plane-protocols/rt:control-plane-protocol/ospf:ospf/ospf:fast-reroute" {
    deviate not-supported;
  }
  deviation "/rt:routing/rt:control-plane-protocols/rt:control-plane-protocol/ospf:ospf/ospf:node-tags" {
    deviate not-supported;
  }
  deviation "/rt:routing/rt:control-plane-protocols/rt:control-plane-protocol/ospf:ospf/ospf:mpls" {
    deviate not-supported;
  }
  deviation "/rt:routing/rt:control-plane-protocols/rt:control-plane-protocol/ospf:ospf/ospf:nsr" {
    deviate not-supported;
  }

  /* OSPF Area */
  deviation "/rt:routing/rt:control-plane-protocols/rt:control-plane-protocol/ospf:ospf/ospf:areas/ospf:area/ospf:area-type" {
    deviate add {
      must "(../ospf:area-id != '0.0.0.0') or "
         + "(derived-from-or-self(., 'ospf:normal-area'))" {
        error-message "Area 0.0.0.0 (backbone) cannot be configured as "
                    + "stub or NSSA.";
        description
          "The backbone area (area 0.0.0.0) must be a normal area. "
        + "It cannot be configured as a stub area or NSSA as per "
        + "RFC 2328 and RFC 3101.";
      }
    }
  }
  deviation "/rt:routing/rt:control-plane-protocols/rt:control-plane-protocol/ospf:ospf/ospf:areas/ospf:area/ospf:virtual-links" {
    deviate not-supported;
  }
  deviation "/rt:routing/rt:control-plane-protocols/rt:control-plane-protocol/ospf:ospf/ospf:areas/ospf:area/ospf:sham-links" {
    deviate not-supported;
  }
  deviation "/rt:routing/rt:control-plane-protocols/rt:control-plane-protocol/ospf:ospf/ospf:areas/ospf:area/ospf:ranges" {
    deviate not-supported;
  }
  deviation "/rt:routing/rt:control-plane-protocols/rt:control-plane-protocol/ospf:ospf/ospf:areas/ospf:area/ospf:database" {
    deviate not-supported;
  }
  deviation "/rt:routing/rt:control-plane-protocols/rt:control-plane-protocol/ospf:ospf/ospf:areas/ospf:area/ospf:topologies" {
    deviate not-supported;
  }

  deviation "/rt:routing/rt:control-plane-protocols/rt:control-plane-protocol/ospf:ospf/ospf:areas/ospf:area/ospf:statistics" {
    deviate not-supported;
  }

  /* OSPF Area Interface */
  deviation "/rt:routing/rt:control-plane-protocols/rt:control-plane-protocol/ospf:ospf/ospf:areas/ospf:area/ospf:interfaces/ospf:interface/ospf:static-neighbors/ospf:neighbor" {
    deviate add {
      must "../../ospf:interface-type = 'point-to-multipoint' or ../../ospf:interface-type = 'non-broadcast'" {
        error-message "Static neighbors are only applicable to point-to-multipoint or non-broadcast interface types.";
      }
    }
  }
  /* OSPFv3 supports only broadcast, point-to-point and multicast
     point-to-multipoint (hybrid) network types -- no non-broadcast (NBMA),
     no unicast point-to-multipoint, and no static neighbors. */
  deviation "/rt:routing/rt:control-plane-protocols/rt:control-plane-protocol/ospf:ospf/ospf:areas/ospf:area/ospf:interfaces/ospf:interface" {
    deviate add {
      must "not(derived-from-or-self(../../../../../rt:type, 'infix-rt:ospfv3')) or "
         + "(not(ospf:interface-type = 'non-broadcast') and "
         + "not(ospf:interface-type = 'point-to-multipoint') and "
         + "count(ospf:static-neighbors/ospf:neighbor) = 0)" {
        error-message "OSPFv3 supports only broadcast, point-to-point and hybrid interfaces, without static neighbors.";
      }
    }
  }
  deviation "/rt:routing/rt:control-plane-protocols/rt:control-plane-protocol/ospf:ospf/ospf:areas/ospf:area/ospf:interfaces/ospf:interface/ospf:multi-areas"    {
    deviate not-supported;
  }
  deviation "/rt:routing/rt:control-plane-protocols/rt:control-plane-protocol/ospf:ospf/ospf:areas/ospf:area/ospf:interfaces/ospf:interface/ospf:node-flag"    {
    deviate not-supported;
  }
  deviation "/rt:routing/rt:control-plane-protocols/rt:control-plane-protocol/ospf:ospf/ospf:areas/ospf:area/ospf:interfaces/ospf:interface/ospf:bfd/ospf:local-multiplier"
  {
    deviate not-supported;
  }
  deviation "/rt:routing/rt:control-plane-protocols/rt:control-plane-protocol/ospf:ospf/ospf:areas/ospf:area/ospf:interfaces/ospf:interface/ospf:bfd/ospf:interval-config-type"
  {
    deviate not-supported;
  }
  deviation "/rt:routing/rt:control-plane-protocols/rt:control-plane-protocol/ospf:ospf/ospf:areas/ospf:area/ospf:interfaces/ospf:interface/ospf:priority"
  {
    deviate add {
      default "1";
    }
    description
      "FRR uses a default priority of 1 for DR/BDR election.
       Setting default to match FRR behavior.";
  }
  deviation "/rt:routing/rt:control-plane-protocols/rt:control-plane-protocol/ospf:ospf/ospf:areas/ospf:area/ospf:interfaces/ospf:interface/ospf:fast-reroute"
  {
    deviate not-supported;
  }
  deviation "/rt:routing/rt:control-plane-protocols/rt:control-plane-protocol/ospf:ospf/ospf:areas/ospf:area/ospf:interfaces/ospf:interface/ospf:authentication"
  {
    deviate not-supported;
  }
  deviation "/rt:routing/rt:control-plane-protocols/rt:control-plane-protocol/ospf:ospf/ospf:areas/ospf:area/ospf:interfaces/ospf:interface/ospf:statistics"
  {
    deviate not-supported;
  }
  deviation "/rt:routing/rt:control-plane-protocols/rt:control-plane-protocol/ospf:ospf/ospf:areas/ospf:area/ospf:interfaces/ospf:interface/ospf:neighbors/ospf:neighbor/ospf:statistics"
  {
    deviate not-supported;
  }
  deviation "/rt:routing/rt:control-plane-protocols/rt:control-plane-protocol/ospf:ospf/ospf:areas/ospf:area/ospf:interfaces/ospf:interface/ospf:neighbors/ospf:neighbor/ospf:cost"
  {
    deviate not-supported;
  }

  deviation "/rt:routing/rt:control-plane-protocols/rt:control-plane-protocol/ospf:ospf/ospf:areas/ospf:area/ospf:interfaces/ospf:interface/ospf:database"
  {
    deviate not-supported;
  }
  deviation "/rt:routing/rt:control-plane-protocols/rt:control-plane-protocol/ospf:ospf/ospf:areas/ospf:area/ospf:interfaces/ospf:interface/ospf:topologies"
  {
    deviate not-supported;
  }
  deviation "/rt:routing/rt:control-plane-protocols/rt:control-plane-protocol/ospf:ospf/ospf:areas/ospf:area/ospf:interfaces/ospf:interface/ospf:instance-id"
  {
    deviate not-supported;
  }
  deviation "/rt:routing/rt:control-plane-protocols/rt:control-plane-protocol/ospf:ospf/ospf:areas/ospf:area/ospf:interfaces/ospf:interface/ospf:interface-id"
  {
    deviate not-supported;
  }
  deviation "/rt:routing/rt:control-plane-protocols/rt:control-plane-protocol/ospf:ospf/ospf:areas/ospf:area/ospf:interfaces/ospf:interface/ospf:demand-circuit"
  {
    deviate not-supported;
  }
  deviation "/rt:routing/rt:control-plane-protocols/rt:control-plane-protocol/ospf:ospf/ospf:areas/ospf:area/ospf:interfaces/ospf:interface/ospf:ttl-security"
  {
    deviate not-supported;
  }
  deviation "/rt:routing/rt:control-plane-protocols/rt:control-plane-protocol/ospf:ospf/ospf:areas/ospf:area/ospf:interfaces/ospf:interface/ospf:lls"
  {
    deviate not-supported;
  }

  deviation "/rt:routing/rt:control-plane-protocols/rt:control-plane-protocol/ospf:ospf/ospf:areas/ospf:area/ospf:interfaces/ospf:interface/ospf:mtu-ignore"
  {
    deviate not-supported;
  }

  deviation "/rt:routing/rt:control-plane-protocols/rt:control-plane-protocol/ospf:ospf/ospf:areas/ospf:area/ospf:interfaces/ospf:interface/ospf:prefix-suppression"
  {
    deviate not-supported;
  }

  /* OSPF RPCs */
  deviation "/ospf:clear-neighbor" {
    deviate not-supported;
  }

  deviation "/ospf:clear-database" {
    deviate not-supported;
  }

  /* OSPF Notifications */
  deviation "/ospf:if-state-change" {
    deviate not-supported;
  }

  deviation "/ospf:if-config-error" {
    deviate not-supported;
  }

  deviation "/ospf:nbr-state-change" {
    deviate not-supported;
  }

  deviation "/ospf:nbr-restart-helper-status-change" {
    deviate not-supported;
  }

  deviation "/ospf:if-rx-bad-packet" {
    deviate not-supported;
  }

  deviation "/ospf:lsdb-approaching-overflow" {
    deviate not-supported;
  }

  deviation "/ospf:lsdb-overflow" {
    deviate not-supported;
  }

  deviation "/ospf:nssa-translator-status-change" {
    deviate not-supported;
  }

  deviation "/ospf:restart-status-change" {
    deviate not-supported;
  }


  /*
   * Augmentations
   */

  /* The route table can be large and moves with every SPF run, so it
   * is read when asked rather than kept as operational data. */
  deviation "/rt:routing/rt:control-plane-protocols/rt:control-plane-protocol/"
          + "ospf:ospf/ospf:local-rib" {
    deviate not-supported;
  }

  augment "/rt:routing/rt:control-plane-protocols/rt:control-plane-protocol/"
        + "ospf:ospf" {
    description
      "Read the OSPF routing table on request.";

    action get-routes {
      description
        "List the routes the OSPF instance has computed.

         The local RIB is not operational data, this action reads it
         from the daemon when asked.  The routes OSPF has installed
         are also in the RIB under ietf-routing.";

      output {
        list route {
          key "prefix";
          description "A route in the OSPF local RIB.";

          leaf prefix {
            type inet:ip-prefix;
            description "Destination prefix.";
          }

          container next-hops {
            description "Next hops for the route.";

            list next-hop {
              description "One next hop.";

              leaf outgoing-interface {
                type if:interface-ref;
                description "Name of the outgoing interface.";
              }

              leaf next-hop {
                type inet:ip-address;
                description "Address of the next hop.";
              }
            }
          }

          leaf metric {
            type uint32;
            description "Metric for this route.";
          }

          leaf route-type {
            type ospf:route-type;
            description "Route type for this route.";
          }

          leaf route-tag {
            type uint32;
            description "Route tag for this route.";
          }

          leaf area-id {
            type ospf:area-id-type;
            description
              "Area the route was learned in.

               Not applicable for inter-area routes learned from area
               border routers or external routes.";
          }
        }
      }
    }
  }

  /* Add uptime to OSPF neighbor operational state
   * The standard ietf-ospf model doesn't include neighbor uptime,
   * but FRR provides this and it's useful for monitoring neighbor stability.
   */
  augment "/rt:routing/rt:control-plane-protocols/rt:control-plane-protocol/"
        + "ospf:ospf/ospf:areas/ospf:area/ospf:interfaces/ospf:interface/"
        + "ospf:neighbors/ospf:neighbor" {
    when "derived-from-or-self(../../../../../../../rt:type, 'infix-rt:ospfv2') or "
       + "derived-from-or-self(../../../../../../../rt:type, 'infix-rt:ospfv3')" {
      description
        "This augmentation is valid for OSPFv2 and OSPFv3.";
    }
    description
      "Infix extension to add uptime information to OSPF neighbors.";

    leaf uptime {
      type uint32;
      units "seconds";
      config false;
      description
        "Time since the neighbor transitioned to the Full state.
         Reported in seconds for consistency with other timers.";
    }

    leaf role {
      type enumeration {
        enum DR {
          description "Designated Router";
        }
        enum BDR {
          description "Backup Designated Router";
        }
        enum DROther {
          description "Neither DR nor BDR";
        }
      }
      config false;
      description
        "OSPF neighbor's role on the network segment (DR, BDR, or DROther).
         This is derived from the neighbor's priority and router ID during
         the DR/BDR election process.";
    }

    leaf interface-name {
      type string;
      config false;
      description
        "Interface name with local address in format 'interface:address'.
         Example: 'e5:10.0.23.1' indicates interface e5 with local address 10.0.23.1.
         This is useful for networks where multiple addresses exist on an interface.";
    }
  }
}
