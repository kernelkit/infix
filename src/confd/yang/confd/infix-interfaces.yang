module infix-interfaces {
  yang-version 1.1;
  namespace "urn:infix:interfaces:ns:yang:1.0";
  prefix infix-if;

  import ietf-interfaces {
    prefix if;
  }
  import ietf-yang-types {
    prefix yang;
  }
  import ietf-inet-types {
    prefix inet;
  }
  import ietf-keystore {
    prefix ks;
  }
  import infix-if-type {
    prefix infix-ift;
  }
  import ietf-hardware {
    prefix iehw;
  }
  import infix-hardware {
    prefix ih;
  }

  include infix-if-base;
  include infix-if-bridge;
  include infix-if-lag;
  include infix-if-container;
  include infix-if-veth;
  include infix-if-vlan;
  include infix-if-gre;
  include infix-if-vxlan;
  include infix-if-wifi;
  include infix-if-wireguard;
  include infix-if-ppp;
  include infix-if-ptp;
  include infix-if-modem;
  include infix-if-qos;

  organization "KernelKit";
  contact      "kernelkit@googlegroups.com";
  description  "Linux bridge and lag extensions for ietf-interfaces.";

  revision 2026-11-11 {
    description "Submodule infix-if-qos: QoS profiles, and the port's
                 egress/rate-limit becomes egress-shaper.";
    reference "internal";
  }

  revision 2026-10-22 {
    description "Add bridge unicast forwarding database and aging time, and
                 operational state for the active IGMP and MLD querier.";
    reference "internal";
  }

  revision 2026-10-11 {
    description "Include infix-if-modem submodule for cellular wwan interfaces.";
    reference "internal";
  }

  revision 2026-10-03 {
    description "Add PPPoE client interfaces.";
    reference "internal";
  }

  revision 2026-09-28 {
    description "Constrain the character set of interface names.";
    reference "internal";
  }

  revision 2026-09-07 {
    description "Add per-interface QoS: ingress classification, traffic
                 class table and transmission selection, see
                 infix-if-qos@2026-09-07.";
    reference "internal";
  }

  revision 2026-06-11 {
    description "Fix WireGuard key-format must expressions, see
                 infix-if-wireguard@2026-06-11.";
    reference "internal";
  }

  revision 2026-05-18 {
    description "Track ieee802-ethernet-interface@2025-09-10 upgrade
                 (IEEE Std 802.3.2-2025): operational data now exposes
                 phy-type/pmd-type leaves and the interface speed via
                 ietf-interfaces:speed (bits/s) rather than the obsolete
                 eth:speed.";
    reference "internal";
  }

  revision 2026-05-13 {
    description "Add limitations on custom mac addresses on interfaces, now needs to be a correct unicast mac-address";
    reference "internal";
  }

  revision 2026-04-29 {
    description "Add operational state for multicast router ports per bridge.";
    reference "internal";
  }

  revision 2026-04-09 {
    description "Add ptp-capabilities submodule for per-interface PTP timestamping info.";
    reference "internal";
  }

  revision 2025-11-06 {
    description "Use new tunnel-common grouping for local, remote, ttl, and tos.";
    reference "internal";
  }

  revision 2025-06-17 {
    description "Add support for Wi-Fi client.";
    reference "internal";
  }

 revision 2025-01-09 {
    description "Add support for link aggregation, static and LACP.";
    reference "internal";
  }

  revision 2025-01-08 {
    description "Add Spanning Tree Protocol (STP) support to bridges.";
    reference "internal";
  }

  revision 2024-11-27 {
    description "Allow IP addresses directly on VLAN filtering bridges.";
    reference "internal";
  }

  revision 2024-11-15 {
    description "Two changes:
                  - Limit name 1-15 chars, Linux limitation
                  - Relocate 'feature containers' to submodule";
    reference "internal";
  }

  revision 2024-10-28 {
    description "Limit description to 64 chars, matching IF-MIB max.";
    reference "internal";
  }

  revision 2024-10-14 {
    description "Deviate link-up-down-trap-enable not-supported.";
    reference "internal";
  }

  revision 2024-10-08 {
    description "Replace writable phy-address with custom-phys-address.";
    reference "internal";
  }

  revision 2024-09-23 {
    description "Drop interfaces-state deviation, already marked deprecated.";
    reference "internal";
  }

  revision 2024-01-15 {
    description "Add support for container ports (CNI networks).";
    reference "internal";
  }

  revision 2023-09-19 {
    description "Add deviation to allow setting phys-address on links.";
    reference "internal";
  }

  revision 2023-08-21 {
    description "Move port augment to submodule for infix-if-bridge and
                 infix-if-lag (later) which reference it.

                 Add deviation to if:type to limit the iana-if-types to
                 only those supported, also reduce list for CLI <TAB>.

                 Lint: move include and import to match canonical order.";
    reference "internal";
  }

  revision 2023-06-05 {
    description "Initial revision.";
    reference "internal";
  }

  grouping tunnel-common {
    description "Common tunnel parameters applicable to all tunnel types.";

    leaf local {
      type inet:ip-address;
      mandatory true;
      description "Local address to use as source address for the tunnel.";
    }

    leaf remote {
      type inet:ip-address;
      must "(contains(../local, ':') and contains(., ':'))
            or (not(contains(../local, ':')) and not(contains(., ':')))" {
        error-message
          "Local and remote must be both IPv4 or both IPv6 addresses.";
      }
      mandatory true;
      description "Remote peer address for the tunnel.";
    }

    leaf ttl {
      type union {
        type uint8 {
          range "1..255";
        }
        type enumeration {
          enum inherit {
            description
              "Copy TTL from inner packet (default kernel behavior).
               WARNING: This can cause issues with protocols like OSPF
               that use TTL=1 for their packets.";
          }
        }
      }
      default 64;
      description
        "Time To Live (TTL) for IPv4 or Hop Limit for IPv6 tunnel packets.
         A fixed value (1-255) sets the outer packet TTL regardless of inner
         packet TTL. The 'inherit' mode copies TTL from the encapsulated packet.

         For OSPF and other routing protocols over tunnels, a fixed value
         (typically 64 or 255) should be used to ensure packets can traverse
         multiple hops between tunnel endpoints.";
    }

    leaf tos {
      type union {
        type uint8;
        type enumeration {
          enum inherit {
            description "Copy ToS/DSCP from inner packet.";
          }
        }
      }
      default "inherit";
      description
        "Type of Service (IPv4) or Traffic Class (IPv6) for tunnel packets.
         Can be a fixed value (0-255) for QoS marking, or 'inherit' to copy
         from the encapsulated packet.";
    }
  }

  /*
   * Data Nodes
   */

  deviation "/if:interfaces/if:interface/if:type" {
    deviate replace {
      type identityref {
        base infix-ift:infix-interface-type;
      }
    }
  }

  deviation "/if:interfaces/if:interface/if:name" {
    deviate replace {
      type string {
        length "1..15";
        pattern '[a-zA-Z0-9_][a-zA-Z0-9_.:+-]*';
      }
    }
    description "Interface names are plain identifiers, at most 15
                 characters (Linux IFNAMSIZ).";
  }

  deviation "/if:interfaces/if:interface/if:description" {
    deviate replace {
      type string {
        length "0..64";
        pattern '[^\p{Cc}]*';
      }
    }
  }

  deviation "/if:interfaces/if:interface/if:link-up-down-trap-enable" {
    deviate not-supported;
  }

  augment "/if:interfaces/if:interface" {
    description "Custom phys-address management, static or derived from chassis MAC.";

    container custom-phys-address {
      description "Override the default physical address.";

      choice type {
        description "Choose between static MAC address or chassis-derived MAC.";

        case static {
          leaf static {
            description "Statically configured unicast MAC address.";
            type yang:mac-address {
              pattern '[0-9a-fA-F][02468aAcCeE]:[0-9a-fA-F]{2}:[0-9a-fA-F]{2}:[0-9a-fA-F]{2}:[0-9a-fA-F]{2}:[0-9a-fA-F]{2}' {
                error-message "Must be a unicast MAC address (multicast bit must not be set).";
              }
            }
          }
        }

        case chassis {
          container chassis {
            description "Derive physical address from chassis MAC address.";
            presence "Enable chassis-derived address.";

            leaf offset {
              description "Static offset added to the chassis MAC address.";
              type yang:mac-address;
            }
          }
        }
      }
    }
  }
}
