submodule infix-if-wlan {
  yang-version 1.1;
  belongs-to infix-interfaces {
    prefix infix-if;
  }
  import ietf-interfaces {
    prefix if;
  }
  import infix-if-type {
    prefix infixift;
  }
  import ietf-netconf-acm {
    prefix nacm;
  }
  import infix-wifi-country-codes {
    prefix iwcc;
  }

  organization "KernelKit";
  contact      "kernelkit@googlegroups.com";
  description
    "WiFi-specific extensions to the standard IETF interfaces model.

     This submodule defines configuration and operational data relevant to
     wireless LAN (WLAN) interfaces, including security settings, network
     discovery, and regulatory compliance.

     It supports WiFi client mode and enables comprehensive management of
     wireless connections, including encryption, country codes, and scanning.";

  revision 2025-05-27 {
    description "Initial revision.";
    reference "internal";
  }

  typedef encryption {
    type enumeration {
      enum WPA {
        description
          "Enables WPA3/WPA2/WPA encryption with automatic protocol
           negotiation. The system uses the strongest supported variant.";
      }
      enum disabled {
        description
          "Disables encryption for an open network.

           WARNING: Open networks transmit data unencrypted and should only
           be used in trusted environments.";
      }
    }
    description
      "Encryption modes available for WiFi connections.

       - WPA: Secure connection using WPA3/WPA2/WPA (auto-selected)
       - disabled: Open network (unencrypted)";
  }

  identity wlan-mode {
    description
      "Base identity for WiFi operating modes.

       Used to define different interface roles such as client, AP, ad-hoc, etc.";
  }

  identity client {
    base wlan-mode;
    description
      "WiFi client (station) mode.

       Connects to an existing wireless network as a station.";
  }

  augment "/if:interfaces/if:interface" {
    when "derived-from-or-self(if:type, 'infixift:wlan')" {
      description
        "Applies only to interfaces of type 'wlan'.";
    }

    container wlan {
      description
        "WiFi-specific configuration and operational data.";

      leaf mode {
        type identityref {
          base wlan-mode;
        }
        description
          "WiFi interface mode, e.g., 'client'.

           Determines how the interface operates within a wireless network.

           May require interface restart after change.";
      }

      leaf country-code {
        mandatory true;
        type iwcc:country-code;
        description
          "Two-letter ISO 3166-1 country code for regulatory compliance.

           Examples: 'US', 'DE', 'JP'.

           WARNING: Incorrect values may violate local laws.";
      }

      leaf encryption {
        default WPA;
        type encryption;
        description
          "WiFi encryption method.

           - WPA (default): Enables WPA3/WPA2/WPA auto-negotiation
           - disabled: Disables encryption (open network)";
      }

      leaf ssid {
        mandatory true;
        type string {
          length "1..32";
        }
        description
          "WiFi network name (SSID).

           Case-sensitive, must match the target network.

           Length: 1–32 characters.";
      }

      leaf secret {
        nacm:default-deny-all;
        type string {
          length "8..63";
        }
        must "../encryption != 'disabled'" {
          error-message
            "Pre-shared key required unless encryption is disabled.";
        }
        description
          "Pre-shared key (PSK) for WPA-secured networks.

           Write-only field.

           Guidelines:
           - 8–63 characters
           - Avoid dictionary words
           - Use random phrases for stronger security";
      }

      leaf rssi {
        config false;
        type int16;
        units "dBm";
        description
          "Current received signal strength (RSSI) in dBm.

           Lower (more negative) values indicate stronger signals.";
      }

      action scan {
        nacm:default-deny-all;
        description
          "Performs an active WiFi scan for nearby networks.

           Discovers SSIDs, signal strength, channel, and security info.

           May impact active connections temporarily.";

        output {
          list ssids {
            key ssid;
            description
              "List of discovered networks.";

            leaf ssid {
              type string;
              description
                "SSID of the discovered network.

                 May be empty for hidden networks.";
            }

            leaf rssi {
              type int16;
              units "dBm";
              description
                "Signal strength of the network.";
            }

            leaf channel {
              type int16;
              description
                "Channel on which the network was detected.";
            }

            leaf security {
              type string;
              description
                "Human-readable description of the detected security.

                 Possible values:
                 - Open
                 - WPA1
                 - WPA2
                 - WPA3
                 - WPA2/WPA3
                 - WEP
                 - Unknown";
            }
          }
        }
      }
    }
  }
}
