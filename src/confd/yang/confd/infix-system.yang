module infix-system {
  yang-version 1.1;
  namespace "urn:infix:system:ns:yang:1.0";
  prefix infix-sys;

  import ietf-system {
    prefix sys;
  }
  import ietf-interfaces {
    prefix if;
  }
  import ietf-yang-types {
    prefix yang;
  }
  import iana-timezones {
    prefix iana-tz;
  }

  import ietf-inet-types {
    prefix inet;
    reference
      "RFC 6991: Common YANG Data Types";
  }

  import infix-schedule {
    prefix infix-schedule;
  }

  import ietf-netconf-acm {
    prefix nacm;
    reference
      "RFC 8341: Network Configuration Access Control Model";
  }

  include infix-system-software;

  organization "KernelKit";
  contact      "kernelkit@googlegroups.com";
  description  "Infix augments and deviations to ietf-system.";

  revision 2026-11-09 {
    description "Explain a rejected hostname in words instead of the pattern.";
    reference "internal";
  }

  revision 2026-10-01 {
    description "Add the check-update RPC (see submodule).";
    reference "internal";
  }

  revision 2026-09-22 {
    description "Add unattended-update, a shared software/update-url naming an
                 RSS/Atom release feed, and allow-prerelease (see submodule).
                 Use the infix-schedule scheduled-feature grouping for
                 scheduled-reboot, adding enabled.";
    reference "internal";
  }

  revision 2026-09-11 {
    description "Add support-collect RPC, returns a support archive inline.";
    reference "internal";
  }

  revision 2026-09-08 {
    description "Add /system/advanced, for low-level system customization:
                  - rc.ds: user scripts run once at boot, extracted from the
                    configuration to /etc/rc.d
                  - defaults: daemon environment files in /etc/default";
    reference "internal";
  }
  revision 2026-09-01 {
    description "Add per-server minpoll/maxpoll to NTP client configuration.";
    reference "internal";
  }
  revision 2026-06-17 {
    description "Add scheduled-reboot, triggered from a referenced schedule.";
    reference "internal";
  }
  revision 2026-03-09 {
    description "Add stratumweight to NTP client configuration.

                 Allows tuning the weight of stratum in NTP source selection
                 relative to measured distance.  Higher values give more preference
                 to lower-stratum sources; use 1.0 to guarantee stratum-based
                 selection on local networks.  Setting to 0.0 disables stratum
                 weighting (pure distance-based selection).";
    reference "internal";
  }

  revision 2025-12-02 {
    description "Extend services with runtime statistics:
                   - Add statistics container with memory-usage, uptime, restart-count";
    reference "internal";
  }
  revision 2025-10-18 {
    description "New system-state status:
                   - Add system resource usage: memory, loadavg, filesystem usage
                   - Add services status";
    reference "internal";
  }
  revision 2025-01-25 {
    description "Add DNS resolver status.";
    reference "internal";
  }
  revision 2024-11-27 {
    description "Add NTP status.";
    reference "internal";
  }
  revision 2024-09-13 {
    description "Add some informative help about different shells and security.";
    reference "internal";
  }

  revision 2024-06-15 {
    description "Merge infix-shell-types.yang to add shell-type identities.";
    reference "internal";
  }

  revision 2024-06-14 {
    description "Add support for format specifiers in hostname:
                   - %h default hostname from /etc/os-release
                   - %i value of ID from /etc/os-release
                   - %m last three octets of base MAC, e.g., c0-ff-ee

                 Add support for yescrypt and $factory$ in password.
                 The latter is a reserved string which is interpreted
                 as the device default password from the VPD EEPROM.";
    reference "internal";
  }

  revision 2024-04-12 {
    description "New type, infix:hostname, for /system/hostname (max 64 chars).";
    reference "internal";
  }

  revision 2024-02-29 {
    description "Mark infix-sys:motd as deprecated, to be replaced with type binary.";
    reference "internal";
  }

  revision 2023-10-19 {
    description "Change deviation for timezone-utc-offset from unsupported to Etc+/-HOUR
                - Unit is set to hours (tzdata compatibility)
                - Range is -12 .. 14";

    reference "internal";
  }

  revision 2023-08-15 {
    description "Add support for user login shell.

                 Update/add deviation specifications:
                  - timezone-name (use tz defs from iana-timezone.yang)
                  - timezone-utc-offset (updated path for 'not-supported')
                  - radius ('not-supported')
                  - dns-resolver port ('not-supported')
                  - authentication username (limit length and pattern)";
    reference "internal";
  }

  revision 2023-04-11 {
    description "Initial revision.";
    reference "internal";
  }

  /*
   * Identities
   */

  identity editor-type {
    description "Base identity from which specific editor types are derived.";
  }

  identity emacs {
    description "Micro Emacs clone (mg).";
    base editor-type;
  }
  identity nano {
    description "GNU Nano.";
    base editor-type;
  }
  identity vi {
    description "The classic UNIX Visual editor.";
    base editor-type;
  }

  identity shell-type {
    description "Base identity from which specific shell types are derived.";
  }

  identity bash {
    description "Bourne again shell (BASH), standard UNIX shell.";
    base shell-type;
  }
  identity clish {
    description "Dedicated switch/router shell, similar to Cisco/JunOS.";
    base shell-type;
  }
  identity sh {
    description "POSIX shell, the original plain UNIX shell.";
    base shell-type;
  }
  identity false {
    description "Shell login disabled, both console and SSH.";
    base shell-type;
  }

  typedef source-state {
    reference "rfc5905: Network Time Protocol Version 4: Protocol and Algorithms Specification";
    type enumeration {
      enum selected {
        description "Selected NTP server for synchronization";
      }
      enum candidate {
        description "Valid for synchronization, is used together with thes elected best server and also acting as backup";
      }
      enum outlier {
        description "Valid timesource but discarded by the clustering algorithm";
      }
      enum unusable {
        description "Unreachable or unresponsable";
      }
      enum falseticker {
        description "suspected of providing incorrect time";
      }
      enum unstable {
        description "Too variable or unstable source";
      }
    }
  }
  typedef source-mode {
    type enumeration  {
      enum server {
        description "Normal NTP server";
      }
      enum peer {
        description "Symmetric peer";
      }
      enum local-clock {
        description "Reference clock";
      }
    }
}
  /*
   * Typedefs
   */

  typedef poll-interval {
    type int8 {
      range "-7..24";
    }
    units "log2 seconds";
    description "NTP poll interval, as log2 seconds.";
  }

  typedef crypt-hash {
    type string {
      pattern
        '$0$.*'
      + '|$1$[a-zA-Z0-9./]{1,8}$[a-zA-Z0-9./]{22}'
      + '|$5$(rounds=\d+$)?[a-zA-Z0-9./]{1,16}$[a-zA-Z0-9./]{43}'
      + '|$6$(rounds=\d+$)?[a-zA-Z0-9./]{1,16}$[a-zA-Z0-9./]{86}'
      + '|$y$[a-zA-Z0-9./]+$[a-zA-Z0-9./]{1,86}$[a-zA-Z0-9./]{43}'
      + '|$factory$.*';
    }
    description
        "This type is used to store passwords using a hash function.  It
         extends the IANA crypt-hash type to support yescrypt as well as
         a reserved string '$factory$', used for device-specific factory
         default hash.  It is up to the underlying system to define this
         further, one example is to use Vital Product Data (VPD), e.g.,
         an onboard EEPROM where a device hash is stored for the initial
         'admin' user.

         A value of this type matches one of the forms:

           $0$<clear text password>
           $<id>$<salt>$<password hash>
           $<id>$<parameter>$<salt>$<password hash>

         The '$0$' prefix signals that the value is clear text, and even
         though it is supported, it is *not* recommended!  When such a
         value is received it passes through multiple subsystems before
         a hash value is calculated and the string '$<id>$<salt>$' or
         $<id>$<parameter>$<salt>$ is prepended and the result is stored
         in the configuration data store.  The hash function used depend
         on end system requirements.

         When any other '$<id>$' prefix is received, the system store it
         'as is' in the configuration data store.

         When a server needs to verify a password given by a user, it
         finds the stored password hash string for that user, extracts
         the salt, and calculates the hash with the salt and given
         password as input.  If the calculated hash value is the same as
         the stored value, the password given by the client is accepted.

         This type defines the following supported hash functions:

           id | hash function | feature
           ---+---------------+-------------------
            1 | MD5           | crypt-hash-md5
            5 | SHA-256       | crypt-hash-sha-256
            6 | SHA-512       | crypt-hash-sha-512
            y | yescrypt      | crypt-hash-yescrypt";
    reference
        "IEEE Std 1003.1-2008 - crypt() function
         RFC 1321: The MD5 Message-Digest Algorithm
         FIPS.180-4.2012: Secure Hash Standard (SHS)";
  }

  typedef username {
    type string {
      pattern "[_a-zA-Z0-9][-._a-zA-Z0-9]*$?";
      length "1..256";
    }
  }

  typedef hostname {
    type string {
      pattern
          '('
        + '(([a-zA-Z0-9_]([a-zA-Z0-9\-_]){0,61})?[a-zA-Z0-9]\.)*'
        + '([a-zA-Z0-9_]([a-zA-Z0-9\-_]){0,61})?[a-zA-Z0-9]\.?'
        + '|%[him]'
        + ')'
        + '([a-zA-Z0-9\-_\.]|%[him])*' {
        error-message "Only letters, digits, '-', '_', '.' and the format specifiers %h, %i and %m are allowed, and the name cannot begin with '-' or '.'.";
      }
      length "1..128";
    }
    description "Linux have the same restrictions as IETF, only shorter.
                 Format specifiers are for, default hostname, ID, and the
                 last three octets in base MAC, e.g., c0-ff-ee";
  }

  /*
   * Data nodes
   */

  augment "/sys:system" {
    description "Augment of ietf-system for modifying /etc/motd.";

    leaf motd {
      description "Legacy MotD (Message of the Day), shown after login.

                   Please note, this is obsolete!  When set it overrides the
                   'motd-banner' setting for backwards compatibility.

                   Instead, use 'motd-banner', which takes a base64 encoded
                   text file as an argument.  For CLI users, edit with the
                   'edit motd-banner' command.";
      status obsolete;      // Replaced with motd-banner (binary)
      type string;
    }

    // From openconfig-system, which also has login-banner (TODO)
    leaf motd-banner {
      description "Message of the Day (MotD), shown after SSH/console login.

                   Base64 encoded (binary) file contents for the system file
                   /etc/motd, displayed after SSH/console login.

                   They system may append additional standard information such
                   as the current system date and time, uptime, last login
                   timestamp, etc.";
      type binary;
    }

    leaf text-editor {
      description "Text editor to use in CLI when editing binary settings.";
      type identityref {
        base editor-type;
      }
      default emacs;
    }
  }

  augment "/sys:system" {
    description "Scheduled reboot of the system.";

    container scheduled-reboot {
      description "Reboot the system on the occurrences of a referenced schedule.

         Without a referenced schedule the system is never rebooted.";

      uses infix-schedule:scheduled-feature;
    }
  }

  augment "/sys:system" {
    description "Advanced, low-level system customization.";
    container advanced {
      nacm:default-deny-write;
      description "Advanced system customization, for debugging and development.

                   Settings in this container reach below the abstractions of the
                   rest of the configuration and are applied as-is by the system.

                   Use with care!";

      container rc.ds {
        description "Scripts run once at boot, in the order listed.

                     Scripts are extracted to /etc/rc.d and run as root, one at a time,
                     at the end of system bootstrap, after the startup configuration has
                     been applied.  A script without a '#!' interpreter line is run by
                     /bin/sh.  Output and exit status are logged to the system log.

                     Changes take effect at the next boot.";

        list rc.d {
          key name;
          ordered-by user;
          description "Script to run at boot, in the order listed.";

          leaf name {
            type string {
              length "1..64";
              pattern '[a-zA-Z0-9_][a-zA-Z0-9_.-]*';
            }
            description "Script name, also used for the file in /etc/rc.d.

                         The list order determines the run order, all script names are
                         prefixed with a unique sequence number to ensure the order.";
          }

          leaf description {
            type string;
            description "Free-form description of what the script does.";
          }

          leaf enabled {
            type boolean;
            default true;
            description "Run this script at boot.

                         Disable to keep the script in the configuration without running it.";
          }

          leaf content {
            type binary;
            mandatory true;
            description "Script contents, base64 encoded.

                         In the CLI, use 'edit content' in the script context to edit
                         it as plain text.";
          }
        }
      }

      container defaults {
        description "Environment files for system daemons, written to /etc/default.

                     Most daemons source /etc/default/NAME at startup for extra command
                     line options, e.g., PTP4L_ARGS in /etc/default/ptp4l.  This allows
                     tuning daemon behavior beyond what the rest of the configuration
                     exposes.

                     Files are written as-is when the configuration is activated, and a
                     system service with the same name, if any, is restarted.  A file
                     that shadows one shipped with the system is restored when the
                     entry is disabled or removed.";

        list default {
          key name;
          description "File in /etc/default, keyed by file name.";

          leaf name {
            type string {
              length "1..64";
              pattern '[a-zA-Z0-9_][a-zA-Z0-9_.-]*';
            }
            description "File name in /etc/default, usually the daemon name.";
          }

          leaf description {
            type string;
            description "Free-form description of what the file changes.";
          }

          leaf enabled {
            type boolean;
            default true;
            description "Install this file in /etc/default.

                         Disable to keep the file in the configuration without installing it.";
          }

          leaf content {
            type binary;
            mandatory true;
            description "File contents, base64 encoded, typically NAME_ARGS=\"...\" assignments.

                         In the CLI, use 'edit content' in the file context to edit it
                         as plain text.";
          }
        }
      }
    }
  }

  /*
   * Deferred: per-script result of the most recent boot.  Requires
   * runparts, or a wrapper, to record per-script exit status.
   *
   * augment "/sys:system-state" {
   *   container advanced {
   *     config false;
   *     container rc.d {
   *       list script {
   *         key name;
   *         leaf name {
   *           type string;
   *         }
   *         leaf status {
   *           type enumeration {
   *             enum ok {
   *               description "Script exited with status zero.";
   *             }
   *             enum failed {
   *               description "Script exited non-zero or was killed by a signal.";
   *             }
   *             enum pending {
   *               description "Configured but not yet run, takes effect at next boot.";
   *             }
   *           }
   *         }
   *         leaf exit-status {
   *           type uint8;
   *           description "Exit status, 128 + signal number if killed by a signal.";
   *         }
   *         leaf started {
   *           type yang:date-and-time;
   *         }
   *         leaf duration {
   *           type uint32;
   *           units "milliseconds";
   *         }
   *       }
   *     }
   *   }
   * }
   */

  augment "/sys:system/sys:ntp" {
    leaf stratum-weight {
      type decimal64 {
        fraction-digits 3;
        range "0.0..max";
      }
      default "0.001";
      units "seconds";
      description
        "Weight of stratum in NTP source selection relative to measured distance.

         Each stratum level adds this many seconds of effective distance when
         comparing candidates.  Higher values give more preference to lower-stratum
         sources.

         The default (0.001 = 1ms per stratum level) is suitable for most networks.
         On a LAN where all servers have similar round-trip times, a lower-stratum
         source wins unless its synchronization distance degrades (e.g., due to
         missed polls) by more than this amount.

         Use 1.0 or larger to guarantee stratum-based selection on local networks
         regardless of transient distance fluctuations.  Setting it to 0.0 disables
         stratum weighting; selection is then based purely on measured
         synchronization distance.";
    }
  }

  augment "/sys:system/sys:ntp/sys:server" {
    description "Per-server poll interval limits for the NTP client.";

    leaf minpoll {
      type poll-interval;
      default "6";
      description
        "Minimum poll interval, default 6 (64 seconds).  Values below
         6 should not be used with public servers on the Internet.";
      reference
        "RFC 5905: Network Time Protocol Version 4: Protocol and
         Algorithms Specification, Section 7.2";
    }

    leaf maxpoll {
      must ". >= ../minpoll" {
        error-message "maxpoll must be greater than or equal to minpoll";
      }
      type poll-interval;
      default "10";
      description
        "Maximum poll interval, default 10 (1024 seconds).";
      reference
        "RFC 5905: Network Time Protocol Version 4: Protocol and
         Algorithms Specification, Section 7.2";
    }
  }

  augment "/sys:system/sys:authentication/sys:user" {
    description "Augment of ietf-system to support setting login shell for users.";
    leaf shell {
      type identityref {
        base shell-type;
      }
      default false;
      description "Set UNIX login shell for user.

                   For security reasons avoid shells bash and sh for non-admin users.
                   This since this may open the system for local security issues.

                   default: none (security)";
    }
  }

  augment "/sys:system-state" {
    container ntp {
      description "NTP status";
      config false;

      container sources {
        list source {
          key address;
          leaf address {
            type inet:ip-address;
            description "Address to NTP server";
          }
          leaf mode {
            type source-mode;
            description "Source mode";
          }
          leaf state {
            type source-state;
            description "Source state";
          }
          leaf stratum {
            type uint8;
            description "Stratum of NTP server";
          }
          leaf poll {
            type uint8;
            description "Interval between transmitted NTP messages, expressed as a power of two in seconds";
          }
        }
      }
    }

    container dns-resolver {
      description "List of active DNS servers";
      config false;

      container options {
        description "Resolver options.";

        leaf timeout {
          description "Number of seconds before resolves tries another server.";
          type uint8;
          units "seconds";
        }
        leaf attempts {
          description "Number of times the resolver reties before giving up.";
          type uint8;
        }
      }

      leaf-list search {
        type inet:domain-name;
        description "Ordered list of domains to search when resolving a host name.";
      }

      list server {
        key "address";

        leaf address {
          description "IP address of DNS server";
          type inet:ip-address;
        }

        leaf origin {
          description "How DNS server was acquired";
          type enumeration {
            enum static {
              description "Statically configured";
            }
            enum dhcp {
              description "Dynamically acquired via DHCP";
            }
          }
        }

        leaf interface {
          type if:interface-ref;
          description "Interface DNS server was learned from, if DHCP";
        }
      }

      container statistics {
        description "DNS resolver statistics";

        leaf cache-size {
          description "Current number of entries in DNS cache";
          type yang:counter32;
        }

        leaf cache-hits {
          description "Number of successful cache lookups";
          type yang:counter64;
        }

        leaf cache-misses {
          description "Number of failed cache lookups";
          type yang:counter64;
        }
      }
    }

    container services {
      description "List of monitored system services (processes)";
      config false;

      list service {
        description "Tracked system service processes.";

        leaf pid {
          type uint32;
          description "Process ID (PID) of the service.";
        }

        leaf name {
          type string;
          description "Name of the service or process.";
        }

        leaf description {
          type string;
          description
            "Short description of the service.";
        }

        leaf status {
          type enumeration {
            enum halted {
              description "Service is halted.";
            }
            enum missing {
              description "Service files or dependencies are missing.";
            }
            enum crashed {
              description "Service has crashed.";
            }
            enum stopped {
              description "Service has been manually stopped.";
            }
            enum busy {
              description "Service is busy.";
            }
            enum restart {
              description "Service is restarting.";
            }
            enum conflict {
              description "Service has a conflict preventing start.";
            }
            enum unknown {
              description "Service is in an unknown state.";
            }
            enum done {
              description "Service task has completed.";
            }
            enum failed {
              description "Service task has failed.";
            }
            enum active {
              description "Run/task type service is active.";
            }
            enum stopping {
              description "Service is in the process of stopping.";
            }
            enum teardown {
              description "Service is performing teardown operations.";
            }
            enum setup {
              description "Service is setting up.";
            }
            enum cleanup {
              description "Service is cleaning up.";
            }
            enum paused {
              description "Service is paused.";
            }
            enum waiting {
              description "Service is waiting for conditions.";
            }
            enum starting {
              description "Service is starting.";
            }
            enum running {
              description "Service is running.";
            }
            enum dead {
              description "Service process is dead.";
            }
          }
          description
            "Detailed current status of the process.";
        }

        container statistics {
          description "Service resource usage and runtime statistics";
          config false;

          leaf memory-usage {
            type uint64;
            units "bytes";
            description "Current memory usage in bytes";
          }

          leaf uptime {
            type uint64;
            units "seconds";
            description "Time service has been running";
          }

          leaf restart-count {
            type uint32;
            description "Number of service restarts";
          }
        }
      }
    }

    container resource-usage {
      description "Runtime system resource usage information";
      config false;

      container memory {
        description "System memory usage";

        leaf total {
          description "Total system memory in kibibytes";
          type uint64;
          units "KiB";
        }

        leaf free {
          description "Free memory in kibibytes";
          type uint64;
          units "KiB";
        }

        leaf available {
          description "Available memory in kibibytes (includes cache that can be reclaimed)";
          type uint64;
          units "KiB";
        }
      }

      container load-average {
        description "System load average";

        leaf load-1min {
          description "1-minute load average";
          type decimal64 {
            fraction-digits 2;
          }
        }

        leaf load-5min {
          description "5-minute load average";
          type decimal64 {
            fraction-digits 2;
          }
        }

        leaf load-15min {
          description "15-minute load average";
          type decimal64 {
            fraction-digits 2;
          }
        }
      }

      list filesystem {
        key "mount-point";
        description "Filesystem usage for mounted filesystems";

        leaf mount-point {
          description "Filesystem mount point (e.g., /, /var, /cfg)";
          type string;
        }

        leaf size {
          description "Total filesystem size in kibibytes";
          type uint64;
          units "KiB";
        }

        leaf used {
          description "Used space in kibibytes";
          type uint64;
          units "KiB";
        }

        leaf available {
          description "Available space in kibibytes";
          type uint64;
          units "KiB";
        }
      }
    }
  }

  deviation "/sys:system/sys:hostname" {
    deviate replace {
      type infix-sys:hostname;
    }
    description "Linux hostname can only be max 64 charachters long.";
  }

  deviation "/sys:system/sys:clock/sys:timezone/sys:timezone-name/sys:timezone-name" {
    deviate replace {
      type iana-tz:iana-timezone;
    }
  }

  deviation "/sys:system/sys:clock/sys:timezone/sys:timezone-utc-offset/sys:timezone-utc-offset" {
    description "Timezone UTC offset should be set in hours, not minutes";
    deviate replace {
      type int16 {
        range "-12 .. 14";
      }
      units "hours";
    }
  }

  deviation "/sys:system/sys:radius" {
    deviate not-supported;
  }

  deviation "/sys:system/sys:dns-resolver/sys:server/sys:transport/sys:udp-and-tcp/sys:udp-and-tcp/sys:port" {
    deviate not-supported;
  }

  deviation "/sys:system/sys:authentication/sys:user/sys:name" {
    deviate replace {
      type infix-sys:username;
    }
  }

  deviation "/sys:system/sys:authentication/sys:user/sys:password" {
    description "Extended password hash, including missing types, and $factory$.";
    deviate replace {
      type infix-sys:crypt-hash;
    }
  }

  rpc support-collect {
    nacm:default-deny-all;
    description
      "Collect support data and return the resulting archive.

       The archive holds system and kernel logs, running and
       operational configuration, and network and hardware state.
       Private keys, password hashes and other secrets are removed from
       the configuration first.

       The archive comes back in 'data', or is left on the device with
       its path in 'filename' when it is too large to return inline.
       Nothing else is kept on the device after a successful call.  If
       collection fails, the error says why and names a log with the
       details.";
    input {
      leaf password {
        type string {
          length "1..255";
        }
        description
          "Encrypt the archive with GPG, using this password, a single
           line.  The management session is already encrypted, this is
           for passing the archive on to someone else afterwards.  Fails
           when the device has no gpg.";
      }
    }
    output {
      leaf size {
        type uint32;
        units bytes;
        description "Size of the archive, before base64 encoding.";
      }
      leaf data {
        type binary;
        description
          "The archive itself.  Omitted when it is larger than the
           inline limit of 16 MiB, see 'filename'.

           Over NETCONF this is a single text node, and libxml2 rejects
           text nodes over 10 MB unless the parser is opened with
           XML_PARSE_HUGE.  Clients built on it, lxml and ncclient among
           them, need that option (huge_tree) to receive an archive
           above about 7.5 MB.  RESTCONF returns JSON and has no such
           limit.";
      }
      leaf filename {
        type string;
        description
          "Path to the archive on the device, in /var/lib/support.
           Present only when the archive was too large to return
           inline; the caller then fetches it.";
      }
    }
  }

}
