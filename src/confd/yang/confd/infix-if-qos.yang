submodule infix-if-qos {
  yang-version 1.1;
  belongs-to infix-interfaces {
    prefix infix-if;
  }

  import ietf-interfaces {
    prefix if;
  }
  import ietf-system {
    prefix sys;
  }
  import ieee802-dot1q-types {
    prefix dot1q-types;
  }
  import infix-qos {
    prefix qos;
  }

  organization "KernelKit";
  contact      "kernelkit@googlegroups.com";
  description  "Per-interface Quality of Service.

     Ingress classification to a (priority, drop precedence) pair,
     priority-to-traffic-class binding, per-traffic-class transmission
     selection, and egress remarking, inline on the interface or by
     reference to a profile under /system/qos-profile, plus a per-port
     egress shaper.  The groupings live in infix-qos.

     Applies to every interface type, with no dependency on a bridge
     model.  IEEE 802.1Q names and types are used where 802.1Q defines
     the concept.

     The credit-based and time-aware shapers come from the IEEE 802.1DC
     modules.  VLAN sub-interface PCP mapping stays in
     infix-if-vlan.yang.";

  revision 2026-10-28 {
    description "Add QoS profiles: the pipeline inline or by reference
                 to /system/qos-profile, a choice.  egress/rate-limit
                 becomes qos/egress-shaper, and feature rate-limit
                 becomes egress-shaper.  capabilities gain
                 supported-offload, the stages the fabric can run.
                 active-profile reports the profile a port runs.";
    reference "internal";
  }

  revision 2026-09-07 {
    description "Initial revision: ingress classification, traffic-class
                 table, transmission selection, and egress remarking.";
    reference "internal";
  }

  /*
   * Features
   */

  /*
   * Enabled where tc tbf offloads to the port shaper, or where the CPU is
   * the forwarding path and software tbf is the real thing.
   */
  feature egress-shaper {
    description "Platform can shape the transmit rate of a whole port.";
  }

  /*
   * Data Nodes
   */

  augment "/if:interfaces/if:interface" {
    description "Per-interface QoS.";

    container qos {
      description "Classification, queueing and shaping of the port.";

      container capabilities {
        config false;
        description "What the platform implements.

           Read these before writing configuration that depends on table
           depth.";

        leaf max-drop-precedence-levels {
          if-feature "qos:drop-eligible or qos:drop-precedence";
          type uint8 {
            range "1..4";
          }
          description "Number of drop-precedence levels.

             Two means only 0 and 1 may be used, which is what a platform
             advertising drop-eligible alone reports.";
        }

        leaf max-traffic-classes {
          type dot1q-types:num-traffic-class-type;
          default 8;
          description "Number of egress traffic classes.

             The port's transmit queue count when that is between two
             and seven.  A port with a single queue has no queue
             structure to respect and gets the kernel's eight classes.";
          reference "12.6.3.1 of IEEE Std 802.1Q-2022";
        }

        leaf-list supported-offload {
          type qos:offload-stage-type;
          description "Pipeline stages the switch fabric can run.

             A stage not listed always runs in the kernel,
             which on a switch covers only CPU-forwarded frames.";
        }

        leaf-list offload {
          type qos:offload-stage-type;
          description "Pipeline stages running in the switch fabric.

             These are the stages the driver has taken into hardware
             with the current configuration.  A supported
             stage missing here fell back to the kernel, e.g. a traffic
             class table the fabric cannot carry.";
        }

        leaf-list supported-trust-order {
          type qos:trust-order-type;
          description "Trust orders the platform accepts.

             none is always accepted.

             An order that is not listed is rejected rather than
             reordered.";
        }
      }

      leaf active-profile {
        config false;
        type string;
        description "The QoS profile the port runs.

           Set when the settings of the port come from a profile.  The
           settings themselves are reported under ingress and egress,
           as read back from the port, with or without a profile.";
      }

      choice source {
        default inline;
        description "The port's own settings, or a profile.

           Defaults apply in the inline case only: a port with a profile
           set has no inline settings.";

        case inline {
          uses qos:ingress;
          uses qos:egress;
        }

        case profile {
          leaf profile {
            type leafref {
              path "/sys:system/qos:qos-profile/qos:name";
            }
            description "The QoS profile this port uses.

               Classification and traffic classes come from the profile;
               the egress shaper stays on the port.";
          }
        }
      }

      /* Applied as a tc tbf root above the scheduler. */
      container egress-shaper {
        if-feature "egress-shaper";
        presence "Shapes the transmit rate of the port.";
        description "Transmit rate shaper of the whole port.

           One token bucket above the traffic classes.  It bounds what
           the port sends in total and knows nothing about classes:
           transmission selection decides which class gets the bounded
           rate.";

        leaf rate {
          type uint64 {
            range "8..max";
          }
          units "bits/second";
          mandatory true;
          description "Sustained transmit rate.";
        }

        leaf burst {
          type uint32 {
            range "1518..max";
          }
          units "bytes";
          description "Bytes that may leave at once on a full bucket.

             Unset, it is sized for ten milliseconds
             at rate, never below one maximum-size frame.";
        }
      }
    }
  }
}
