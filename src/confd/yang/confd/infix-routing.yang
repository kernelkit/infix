module infix-routing {
  yang-version 1.1;
  namespace "urn:infix:routing:ns:yang:1.0";
  prefix infix-rt;

  import ietf-routing {
    prefix rt;
  }
  import ietf-ipv4-unicast-routing {
    prefix v4ur;
  }
  import ietf-ipv6-unicast-routing {
    prefix v6ur;
  }
  import ietf-ospf {
    prefix ospf;
  }
  import ietf-bfd-types {
    prefix bfd-types;
  }
  import ietf-rip {
    prefix rip;
  }

  organization "KernelKit";
  contact      "kernelkit@googlegroups.com";
  description  "Deviations and augments for ietf-routing.";

  revision 2026-10-07 {
    description "Move the ietf-ospf and ietf-rip deviations and augments
                 to infix-ospf and infix-rip, which are installed only on
                 devices with dynamic routing.";
    reference "internal";
  }

  revision 2026-09-28 {
    description "Add ospf, rip, and bfd features, where ospf covers OSPFv2
                 and OSPFv3, and rip covers RIPv2 and RIPng.  A build without
                 FRR leaves them off, so only static routes can be configured
                 and the device advertises exactly what it supports.";
    reference "internal";
  }

  revision 2026-07-22 {
    description "Add IPv6 dynamic routing support (RIPng and OSPFv3).
                 Introduce the ripng and ospfv3 routing-type identities,
                 expose the ietf-rip IPv6 address-family for RIPng (previously
                 deviated not-supported), restrict OSPFv3 interfaces to the
                 supported network types (no non-broadcast, no unicast
                 point-to-multipoint, no static neighbors), and extend the OSPF
                 local-rib and neighbor augments to OSPFv3.  Require
                 explicit-router-id for OSPFv3, there is no IPv4 interface
                 address to derive a router ID from.  The OSPF address-family
                 leaf remains not-supported: OSPFv3 carries IPv6 only, IPv4
                 over OSPFv3 (RFC 5838) is not supported.";
    reference "RFC 8695, RFC 2080, RFC 5340, RFC 9129";
  }

  revision 2026-03-11 {
    description "Remove interface-type deviation to expose standard ietf-ospf
                 interface types including point-to-multipoint and hybrid.
                 Un-deviate static-neighbors for non-broadcast P2MP support.";
  }

  revision 2025-12-02 {
    description "Add configurable OSPF debug logging container.
                 Add RIP (Routing Information Protocol) support.";
    reference "RFC 8695";
  }

  revision 2025-11-12 {
    description "Add area-id augmentation to OSPF local-rib routes.
                 Add uptime, role, and interface-name augmentations to OSPF neighbor state.
                 Allows displaying which area a route was learned from,
                 how long neighbors have been up, their DR/BDR role, and
                 the interface with local address.";
    reference "internal";
  }

  revision 2025-11-11 {
    description "Add BFD IP single-hop support (RFC 9127).
                 Deviate session-statistics (not implemented yet).";
    reference "RFC 9127";
  }
  revision 2025-11-10 {
    description "Add must constraint to prevent backbone area as stub/NSSA.
                 Enable OSPF operational data for CLI: un-deviate priority,
                 hello-timer, wait-timer, route metric and route-tag fields.";
    reference "RFC 2328, RFC 3101";
  }
  revision 2024-11-27 {
    description "Deviate address-family in OSPF";
    reference "internal";
  }
  revision 2024-11-15 {
    description "Fix pyang linter errors and warnings:
                  - Drop OSPF database deviations, already deviated earlier
                  - Drop unused imports";
    reference "internal";
  }
  revision 2024-10-01 {
    description "Remove possibility to have loopack in multiple areas.";
    reference "internal";
  }
  revision 2024-09-23 {
    description "Augment static routes with optional route-preference (distance).";
    reference "internal";
  }
  revision 2024-09-22 {
    description "- Enable OSPF route metrics in RIB
                 - Enable 'active' route flag for RIB
                 - Enable 'last-updated' route field for RIB
                 - Augment route in RIB with 'installed' flag
                 - Aadjust YANG prefix for consistency: ietf-r: -> rt:";
    reference "internal";
  }
  revision 2024-09-21 {
    description "Drop RIB source-protocol deviation for standard, add kernel proto.";
    reference "internal";
  }
  revision 2024-09-20 {
    description "Deviate to only show supported routing types";
    reference "internal";
  }
  revision 2024-09-13 {
    description "Declare deviations for non-supported OSPF RPCs and Notifications";
    reference "internal";
  }
  revision 2024-03-06 {
    description "Obsolete leaf enable in favor for enabled in default-route-advertise";
    reference "internal";
  }
  revision 2024-01-09 {
    description "Add operational, area, bfd support
                 and other minor features";
    reference "internal";
  }
  revision 2023-11-23 {
    description "Limit to one instance per control plane protocol,
                 and change to infix (iproute2) specific source protocol names
                 for routes";
    reference "internal";
  }
  revision 2023-10-27 {
    description "Initial revision.";
    reference "internal";
  }

  /* General routing */

  deviation "/rt:routing/rt:router-id" {
    description "Set in OSPF";
    deviate not-supported;
  }
  deviation "/rt:routing-state" {
    description "Obsolete";
    deviate not-supported;
  }

  feature ospf {
    description "OSPFv2 and OSPFv3 dynamic routing, provided by FRR.";
  }
  feature rip {
    description "RIPv2 and RIPng dynamic routing, provided by FRR.";
  }
  feature bfd {
    description "Bidirectional Forwarding Detection, provided by FRR.";
  }

  identity kernel {
    base rt:routing-protocol;
    description
      "'Kernel' routing pseudo-protocol.";
  }

  typedef infix-distribute-protocol {
    type enumeration {
      enum ospf {
        description "Redistribute OSPF routes";
      }
      enum rip {
        description "Redistribute RIP routes";
      }
      enum static {
        description "Redistribute Static routes";
      }
      enum connected {
        description "Redistribute Connected routes";
      }
    }
  }

  identity infix-routing-type {
    description "Infix routing type";
  }
  identity ospfv2 {
    if-feature "ospf";
    base ospf:ospfv2;
    base infix-routing-type;
    description "OSPFv2 (IPv4) routing protocol";
  }
  identity ospfv3 {
    if-feature "ospf";
    base ospf:ospfv3;
    base infix-routing-type;
    description "OSPFv3 (IPv6) routing protocol";
  }
  identity ripv2 {
    if-feature "rip";
    base rip:ripv2;
    base infix-routing-type;
    description "RIPv2 (IPv4) routing protocol";
  }
  identity ripng {
    if-feature "rip";
    base rip:ripng;
    base infix-routing-type;
    description "RIPng (IPv6) routing protocol";
  }
  identity bfdv1 {
    if-feature "bfd";
    base bfd-types:bfdv1;
    base infix-routing-type;
    description "BFD protocol version 1";
  }
  identity static {
    base rt:static;
    base infix-routing-type;
    description "Static route";
  }

  deviation "/rt:routing/rt:control-plane-protocols/rt:control-plane-protocol/rt:type" {
    deviate replace {
      type identityref {
        base infix-routing-type;
      }
    }
  }

  /* Static routes */
  typedef distance {
     description "Capped IETF route-preference, 0-255, for distance.";
     type rt:route-preference {
       range "0..255";
     }
  }

  grouping route-pref {
     leaf route-preference {
       description "Adjust preference between routes of same destination prefix.

                    This attribute, also known as 'administrative distance', allows
                    for selecting the preferred route among routes with the same
                    destination prefix.  A smaller value indicates a route that is
                    more preferred.";
       type distance;
     }
  }

  deviation "/rt:routing/rt:control-plane-protocols/rt:control-plane-protocol/rt:static-routes/v4ur:ipv4/v4ur:route/v4ur:next-hop/v4ur:next-hop-options/v4ur:next-hop-list" {
    deviate not-supported;
  }
  deviation "/rt:routing/rt:control-plane-protocols/rt:control-plane-protocol/rt:static-routes/v6ur:ipv6/v6ur:route/v6ur:next-hop/v6ur:next-hop-options/v6ur:next-hop-list" {
    deviate not-supported;
  }
  augment "/rt:routing/rt:control-plane-protocols/rt:control-plane-protocol/rt:static-routes/v4ur:ipv4/v4ur:route" {
    uses route-pref {
      refine route-preference {
        default "1";
      }
    }
  }
  augment "/rt:routing/rt:control-plane-protocols/rt:control-plane-protocol/rt:static-routes/v6ur:ipv6/v6ur:route" {
    uses route-pref {
      refine route-preference {
        default "1";
      }
    }
  }

  /* show routes */
  deviation "/rt:routing/rt:ribs/rt:rib/rt:default-rib" {
    deviate not-supported;
  }
  deviation "/rt:routing/rt:ribs/rt:rib/rt:active-route" {
    deviate not-supported;
  }
  deviation "/rt:routing/rt:ribs/rt:rib/rt:description" {
    deviate not-supported;
  }
  augment "/rt:routing/rt:ribs/rt:rib/rt:routes/rt:route/"
        + "rt:next-hop/rt:next-hop-options/rt:next-hop-list/"
        + "rt:next-hop-list/rt:next-hop" {
    description "IETF use 'active' for selected routes within a protocol (RIB).
                 This augment adds an 'installed' leaf for marking routes that
                 are installed in the kernel FIB with the given next-hop.";
    leaf installed {
      description "The presence of this leaf indicates that the route is
                   installed in the kernel FIB with the given next-hop.";
      type empty;
    }
  }

  deviation "/rt:routing/rt:control-plane-protocols/rt:control-plane-protocol" {
    deviate add {
      must "count(../control-plane-protocol[type = current()/type]) = 1" {
        error-message "Only one instance per routing protocol is allowed.";
      }
    }
  }
}
