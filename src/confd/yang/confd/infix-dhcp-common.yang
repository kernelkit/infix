module infix-dhcp-common {
  yang-version 1.1;
  namespace "urn:infix:params:xml:ns:yang:dhcp-common";
  prefix dhcp;

  organization "KernelKit";
  contact      "kernelkit@googlegroups.com";
  description  "Shared types between DHCP server and client.";

  revision 2025-12-21 {
    description "Reorder enum values to ascending order, see https://github.com/CESNET/libyang/issues/2462";
    reference "internal";
  }
  revision 2025-11-09 {
    description "Add DHCPv6 options typedef and DHCPv4 vendor-class option.";
    reference "internal";
  }
  revision 2025-01-29 {
    description "Initial revision.";
    reference "internal";
  }

  /*
   * Typedefs
   */

  typedef options {
    description "DHCP options for client and server.";
    type union {
      type uint8 {
          range "1..254";
      }
      type enumeration {
        enum netmask {
          value 1;
          description "IP subnet mask as per RFC 950

                       Note: this option is always sent using a netmask derived from an
                       interface matching the given subnet, even if no configuration
                       exists in global/subnet/host scope.  Except in the case when the
                       server responds to a relayed request, in which case the subnet
                       will not match any local interface.";
        }
        enum router {
          value 3;
          description "Default route, or gateway (single, see also option 121)";
        }
        enum dns-server {
          value 6;
          description "DNS server";
        }
        enum log-server {
          value 7;
          description "Name or IP address of remote syslog server";
        }
        enum hostname {
          value 12;
          description "Hostname";
        }
        enum domain {
          value 15;
          description "Domain name";
        }
        enum broadcast {
          value 28;
          description "IP broadcast address as per RFC 1122

                       Note: this option is always sent using a broadcast address from
                       an interface matching the given subnet, even if no configuration
                       exists in global/subnet/host scope.  Except in the case when the
                       server responds to a relayed request, in which case the subnet will
                       not match any local interface.";
        }
        enum static-route {
          value 33;
          description "Classful (A/B/C network) route(s), use option 121 instead";
        }
        enum ntp-server {
          value 42;
          description "NTP server";
        }
        enum address {
          value 50;
          description "Request (previously cached) address";
        }
        enum vendor-class {
          value 60;
          description "Vendor class, e.g., product name, type/model";
        }
        enum client-id {
          value 61;
          description "Client ID (default MAC, and option 12)";
        }
        enum tftp-server {
          value 66;
          description "TFTP server";
        }
        enum bootfile {
          value 67;
          description "Boot filename from TFTP server (option 66)";
        }
        enum fqdn {
          value 81;
          description "Client request DNS update of FQDN argument, see RFC 4702";
        }
        enum search {
          value 119;
          description "Domain search list";
        }
        enum classless-static-route {
          value 121;
          description "Classless static route(s), tuple: subnet/len, next-hop";
        }
        enum ms-classless-static-route {
          value 249;
          description "Microsoft classless static route(s), same as option 121";
        }
      }
    }
  }

  typedef octet-string {
    description "A generic string or a hex values.";
    type string {
      pattern '([0-9a-fA-F]{2}:)*[0-9a-fA-F]{2}';
    }
  }

  typedef duid {
    description "DHCPv6 Unique Identifier (DUID), RFC 8415 section 11.

                 A DUID consists of a two-octet type code and a variable length
                 identifier field. The minimum length is 4 octets (type + data).

                 Common DUID types:
                 - DUID-LLT (type 1): Link-layer address plus time
                 - DUID-EN (type 2): Enterprise number
                 - DUID-LL (type 3): Link-layer address
                 - DUID-UUID (type 4): UUID

                 Format: Colon-separated hex octets, minimum 4 octets.
                 Example: 00:03:00:01:08:00:27:fe:8c:2a (DUID-LL with Ethernet MAC)";
    type string {
      pattern '([0-9a-fA-F]{2}:){3,}[0-9a-fA-F]{2}';
      /* Minimum 4 octets: ([0-9a-fA-F]{2}:){3,} matches at least 3 colons,
       * plus final [0-9a-fA-F]{2} makes 4 octets total */
    }
  }

  typedef options-v6 {
    description "DHCPv6 options for client.";
    type union {
      type uint16 {
          range "1..65535";
      }
      type enumeration {
        enum client-id {
          value 1;
          description "Client Identifier (DUID), RFC 8415.
                       Automatically generated by default.";
        }
        enum server-id {
          value 2;
          description "Server Identifier (DUID), RFC 8415.";
        }
        enum dns-server {
          value 23;
          description "DNS recursive name servers, RFC 3646.";
        }
        enum domain-search {
          value 24;
          description "Domain search list, RFC 3646.";
        }
        enum ia-pd {
          value 25;
          description "Identity Association for Prefix Delegation, RFC 8415.";
        }
        enum sntp-server {
          value 31;
          description "Simple Network Time Protocol servers, RFC 4075.";
        }
        enum information-refresh-time {
          value 32;
          description "Information refresh time for stateless DHCPv6, RFC 8415.";
        }
        enum client-fqdn {
          value 39;
          description "Client Fully Qualified Domain Name, RFC 4704.";
        }
        enum ntp-server {
          value 56;
          description "NTP time servers, RFC 5908.";
        }
      }
    }
  }
}
