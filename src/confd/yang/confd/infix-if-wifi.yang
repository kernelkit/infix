submodule infix-if-wifi {
  yang-version 1.1;
  belongs-to infix-interfaces {
    prefix infix-if;
  }
  import ietf-interfaces {
    prefix if;
  }
  import ietf-yang-types {
    prefix yang;
  }
  import ietf-netconf-acm {
    prefix nacm;
  }
  import ietf-keystore {
    prefix ks;
  }
  import infix-crypto-types {
    prefix ixct;
  }
  import infix-if-type {
    prefix infixift;
  }
  import ietf-hardware {
    prefix iehw;
  }
  import infix-hardware {
    prefix ih;
  }

  organization "KernelKit";
  contact      "kernelkit@googlegroups.com";
  description
    "Wi-Fi-specific extensions to the standard IETF interfaces model.

     This submodule defines configuration and operational data for Wi-Fi
     virtual interfaces, supporting both Access Point (AP) and Station
     (client) modes.

     Wi-Fi virtual interfaces are created on top of Wi-Fi radios (PHYs)
     defined in the infix-wifi-radio module. The radio provides physical
     layer configuration (channel, power, PHY mode), while virtual
     interfaces provide network-layer configuration (SSID, security).

     Key features:
     - Modes: Access Point, Station, 802.11s Mesh Point and 4-address
       (WDS) link
     - Multi-SSID: Multiple APs on same radio
     - Security: WPA2/WPA3 with keystore integration
     - Operational state: Connection status, RSSI, client lists";

  revision 2026-11-02 {
    description
      "A radio may hold several station or mesh point interfaces as long
       as only one of them is enabled.";
    reference "internal";
  }

  revision 2026-10-06 {
    description
      "Access point and mesh point require the box-wide Wi-Fi country code,
       the per-radio country-code leaf is gone.  802.11r gets an optional
       key-holder-secret, a key of its own for the access points of a
       mobility domain to hand each other a client's keys with, instead
       of the Wi-Fi password.  Interfaces without a custom-phys-address
       are no longer limited to one per radio.  An open access point is
       rejected on 6 GHz, as the error message always said.";
    reference "internal";
  }

  revision 2026-10-02 {
    description
      "Add 4-address (WDS) support: wds-link mode for access point side
       ports, and the station leaves 'wds' and 'peer-bssid'.";
    reference "internal";
  }

  revision 2026-09-24 {
    description
      "Constrain the character set of mesh-id and nas-identifier.";
    reference "internal";
  }

  revision 2026-07-01 {
    description
      "Add station 'bssid' operational leaf: the BSSID the station is
       currently associated to, to tell roaming-ESS access points apart.";
    reference "internal";
  }

  revision 2026-03-06 {
    description
      "Adding mesh support and roaming.
	- Add 802.11s mesh point mode support.
        - Add band-steering (MBO) support and OKC configuration.
        - Add support for roaming, by adding support for 802.11v/k/r";
    reference "internal";
  }

  revision 2025-12-17 {
    description
      "Major refactoring for AP mode support (BREAKING CHANGE):
       - Added radio reference (parent PHY)
       - Added wifi-mode choice (AP vs Station)
       - Reorganized configuration hierarchy
       - Old configurations must be migrated manually";
    reference "internal";
  }

  revision 2025-12-12 {
    description "Adapt to new revision of model ietf-keystore.";
    reference "internal";
  }

  revision 2025-05-27 {
    description "Initial revision (Station mode only).";
    reference "internal";
  }

  feature wifi {
    description "Wi-Fi support is an optional build-time feature in Infix.";
  }

  typedef mobility-domain {
    type union {
      type string {
        pattern '[0-9a-fA-F]{4}';
      }
      type enumeration {
        enum hash {
          description
            "Derive mobility domain by hashing the SSID.

             OpenWrt-compatible: md5(ssid), first 4 hex chars.";
        }
      }
    }
    default "4f57";
    description
      "802.11r Mobility Domain identifier (4 hex digits).

       Use 'hash' to automatically derive it from the SSID.";
  }

  augment "/if:interfaces/if:interface" {
    when "derived-from-or-self(if:type, 'infixift:wifi')" {
      description
        "Applies only to interfaces of type 'wifi'.";
    }
    container wifi {
      if-feature wifi;

      description
        "Wi-Fi virtual interface configuration.

         Each Wi-Fi interface represents a virtual interface (VAP - Virtual
         Access Point, or Station) created on a physical radio.

         The interface must reference a radio defined in infix-wifi-radio
         module, which provides the physical layer configuration.";

      must "radio or wds-link" {
        error-message "A Wi-Fi interface must reference a radio";
      }

      leaf radio {
        type leafref {
          path "/iehw:hardware/iehw:component/iehw:name";
        }
        must "derived-from-or-self(/iehw:hardware/iehw:component[iehw:name=current()]/iehw:class, 'ih:wifi')" {
          error-message "Referenced hardware component must be a Wi-Fi radio (class 'ih:wifi')";
        }
        must "count(/if:interfaces/if:interface[wifi/radio = current()][not(wifi/access-point)][not(wifi/wds-link)][if:enabled = 'true']) <= 1" {
          error-message "Only one enabled station interface is allowed per radio";
        }

        description
          "Reference to parent Wi-Fi radio (PHY).

           References a hardware component with class 'ih:wifi'.
           The radio must exist and be configured before creating
           virtual interfaces.  Not set for a WDS link, which uses
           the radio of its access point.

           Example: 'phy0' for the first Wi-Fi radio.

           All physical layer settings (channel, power, regulatory)
           are inherited from the radio configuration.";
      }

      choice wifi-mode {
        description
          "Wi-Fi interface operating mode.

           An interface without a mode is created but idle.  To find
           the networks in range, use the scan action on the radio.

           Configure one of:
           - Station mode: Connect to an existing Wi-Fi network
           - Access Point mode: Create a Wi-Fi network for clients
           - Mesh Point mode: Create an 802.11s mesh link
           - WDS link: Bridge port for one 4-address station on a local
             access point

           Note: A radio can host either:
           - Multiple AP interfaces (multi-SSID), with WDS links, OR
           - A single Station interface, OR
           - A single Mesh Point interface

           Mixing AP and Mesh Point on the same radio is not supported.";

        case station {
          container station {
            presence "Configure Wi-Fi station (client) mode";

            description
              "Wi-Fi Station mode configuration.

               In station mode, the interface acts as a Wi-Fi client,
               connecting to an existing Access Point.

               Only one station interface is allowed per radio.

               Example use case: Connect to upstream Wi-Fi network.";

            leaf wds {
              type boolean;
              default false;
              description
                "4-address (WDS) mode.

                 Lets the station forward frames for other devices, which
                 is what allows it to be a bridge port.  Use it to bridge
                 the station with wired ports or a local access point, as
                 in a repeater.  The access point must accept 4-address
                 stations, see the wds-link mode.";
            }

            leaf peer-bssid {
              type yang:mac-address;
              description
                "Only associate to the access point with this BSSID.

                 Without it the station picks any access point advertising
                 the SSID.";
            }

            container roaming {
              description
                "Move to a better access point of the network.

                 While connected, the station scans every 30 seconds
                 when the signal is below the threshold, otherwise every
                 10 minutes, and moves to a clearly stronger access
                 point of the same SSID.  Traffic pauses briefly during
                 a scan.  Without roaming, the station moves only when
                 it loses its access point or is asked to move by it.

                 Has no effect with peer-bssid set.";

              leaf enabled {
                type boolean;
                default true;
                description
                  "Look for a better access point while connected.

                   Disable on a fixed link where no scan may pause
                   traffic.";
              }

              leaf signal-threshold {
                type int8 {
                  range "-100..-30";
                }
                units "dBm";
                default -75;
                description
                  "Signal strength below which the station scans often.

                   A higher value finds a better access point sooner, at
                   the cost of more frequent scans.";
              }
            }

            leaf ssid {
              type string {
                length "1..32";
                pattern '[^\x00-\x1f\x22\x5c\x7f]*' {
                  error-message "SSID must not contain control characters, double quotes, or backslashes.";
                }
              }
              mandatory true;
              description
                "Wi-Fi network name (SSID) to connect to.

                 Case-sensitive, must match the target network exactly.

                 Length: 1–32 characters.";
            }

            container security {
              description
                "Wi-Fi security configuration.";

              leaf mode {
                type enumeration {
                  enum auto {
                    description
                      "Automatic security negotiation.
                       Tries WPA3-SAE, then WPA2-PSK, in that order.
                       Recommended for maximum compatibility and security.";
                  }
                  enum disabled {
                    description
                      "Open network (no security).

                       WARNING: All traffic is transmitted unencrypted!
                       Only use in trusted environments.";
                  }
                }
                default auto;
                description
                  "Security mode for Wi-Fi connection.

                   - auto (default): WPA3/WPA2 auto-negotiation (secure)
                   - disabled: Open network (insecure)";
              }

              leaf secret {
                when "../mode != 'disabled'";
                type ks:central-symmetric-key-ref;
                mandatory true;
                description
                  "Pre-shared key (PSK) reference.

                   References a symmetric key in the keystore.

                   For WPA2/WPA3 networks, this is the Wi-Fi password.";
              }
            }

            /* Operational state */

            leaf bssid {
              config false;
              type yang:mac-address;
              description
                "BSSID (MAC address) of the access point the station is
                 currently associated to.

                 Only present while connected.  With several access points
                 sharing one SSID (a roaming ESS), this identifies which one
                 the station is on.";
            }

            leaf signal-strength {
              config false;
              type int16;
              units "dBm";
              description
                "Current signal strength in dBm.

                 More negative values indicate weaker signal.

                 Typical values:
                 - -30 to -50 dBm: Excellent
                 - -50 to -60 dBm: Good
                 - -60 to -70 dBm: Fair
                 - -70 to -80 dBm: Weak
                 - Below -80 dBm: Very weak";
            }

            leaf rx-speed {
              config false;
              type uint32;
              units "100 kbps";
              description
                "Last received data rate from the access point in 100 kbps.

                 Only available when connected.

                 Examples:
                 - 10 = 1 Mbps
                 - 65 = 6.5 Mbps
                 - 866 = 86.6 Mbps";
            }

            leaf tx-speed {
              config false;
              type uint32;
              units "100 kbps";
              description
                "Last transmitted data rate to the access point in 100 kbps.

                 Only available when connected.

                 Examples:
                 - 10 = 1 Mbps
                 - 65 = 6.5 Mbps
                 - 866 = 86.6 Mbps";
            }
          }
        }

        case access-point {
          container access-point {
            presence "Configure Wi-Fi Access Point mode";

            description
              "Wi-Fi Access Point mode configuration.

               In AP mode, the interface provides a Wi-Fi network that
               clients can connect to.

               Multiple AP interfaces can be created on the same radio
               for multi-SSID support (Guest network, IoT network, etc.).

               Example use case: Create Wi-Fi hotspot.";

            must "/iehw:hardware/iehw:component[iehw:name = current()/../radio]/ih:wifi-radio/ih:band" {
              error-message "Parent radio must have 'band' configured for Access Point mode";
            }

            must "/iehw:hardware/iehw:component[iehw:name = current()/../radio]/ih:wifi-radio/ih:channel" {
              error-message "Parent radio must have 'channel' configured for Access Point mode";
            }

            must "/iehw:hardware/ih:wifi/ih:country-code != '00'" {
              error-message "Set the Wi-Fi country code (hardware wifi country-code) before configuring an access point, the world domain '00' is not allowed.";
            }

            leaf ssid {
              type string {
                length "1..32";
                pattern '[^\x00-\x1f\x22\x5c\x7f]*' {
                  error-message "SSID must not contain control characters, double quotes, or backslashes.";
                }
              }
              mandatory true;
              description
                "Wi-Fi network name (SSID) to broadcast.

                 This is the network name that clients will see when
                 scanning for Wi-Fi networks.

                 Length: 1–32 characters.";
            }

            leaf hidden {
              type boolean;
              default false;
              description
                "Hide the SSID from broadcast beacons.

                 When true, the network will not appear in Wi-Fi scans.
                 Clients must know the exact SSID to connect.

                 Note: This provides minimal security benefit and may
                 cause compatibility issues with some clients.";
            }

            container security {
              description
                "Wi-Fi security configuration.";

              leaf mode {
                type enumeration {
                  enum open {
                    description
                      "Open network (no encryption).

                       WARNING: All client traffic is unencrypted!
                       Only use in controlled environments (captive portal, etc.).";
                  }
                  enum auto {
                    description
                      "Automatic security based on radio band.

                       Uses WPA2/WPA3 transitional mode on 2.4GHz and 5GHz,
                       and WPA3-only (SAE) on 6GHz as required by specification.";
                  }
                  enum wpa2-personal {
                    description
                      "WPA2-Personal (WPA2-PSK).
                       Widely compatible, secure for most use cases.";
                  }
                  enum wpa3-personal {
                    description
                      "WPA3-Personal (WPA3-SAE).
                       Enhanced security with forward secrecy.
                       Requires WPA3-capable clients.";
                  }
                  enum wpa2-wpa3-personal {
                    description
                      "WPA2/WPA3 transitional mode.
                       Accepts both WPA2 and WPA3 clients.
                       Recommended for maximum compatibility + security.";
                  }
                }
                default auto;
                must ". = 'auto' or . = 'wpa3-personal' or "
                   + "/iehw:hardware/iehw:component[iehw:name = current()/../../../radio]/ih:wifi-radio/ih:band != '6GHz'" {
                  error-message "6GHz band requires 'auto' or 'wpa3-personal' security mode.";
                }
                description
                  "Wi-Fi security mode.

                   Determines authentication and encryption methods.

                   Recommended: auto for band-aware defaults, or
                   wpa2-wpa3-personal for best compatibility on 2.4/5 GHz.";
              }

              leaf secret {
                when "../mode != 'open'";
                type ks:central-symmetric-key-ref;
                mandatory true;
                description
                  "Pre-shared key (PSK) reference.

                   References a symmetric key in the keystore.

                   This is the Wi-Fi password that clients must provide
                   to connect to the network.

                   Requirements:
                   - WPA2/WPA3: 8-63 characters (configured in keystore)";
              }
            }

            container roaming {
              description
                "Fast roaming and seamless handoff configuration.

                 802.11k: Radio Resource Management (neighbor discovery)
                 802.11r: Fast BSS Transition (fast handoff)
                 802.11v: BSS Transition Management (network-assisted roaming)";

              container dot11k {
                presence "Enable 802.11k Radio Resource Management";
                description
                  "Enable 802.11k Radio Resource Management.

                   Allows clients to discover neighboring APs for better
                   roaming decisions. Enables:
                   - Neighbor reports
                   - Beacon reports";
              }

              container dot11r {
                presence "Enable 802.11r Fast BSS Transition";
                must "../../security/mode != 'open'" {
                  error-message "802.11r requires WPA2/WPA3 security and cannot be used with open networks.";
                }
                description
                  "Enable 802.11r Fast BSS Transition.

                   Reduces handoff latency from ~1s to <50ms through
                   pre-authentication. Required for seamless roaming.";

                leaf key-holder-secret {
                  type ks:central-symmetric-key-ref;
                  description
                    "Secret the access points of the mobility domain use
                     to hand each other a roaming client's keys.

                     References a symmetric key in the keystore.  Set the
                     same key on every device with an access point in the
                     mobility domain.  Without it the Wi-Fi password is
                     used, which lets anyone who knows the password read
                     the other clients' keys.  Give it a value of its own
                     on networks where that matters.";
                }

                leaf mobility-domain {
                  type mobility-domain;
                  default "4f57";
                  description
                    "802.11r Mobility Domain identifier.

                     All APs that clients should roam between MUST use the
                     same mobility domain ID.

                     Can be either:
                     - A 4-character hex string (e.g., '4f57')
                     - 'hash' to auto-derive from SSID (OpenWrt-compatible)";
                }

                leaf nas-identifier {
                  type union {
                    type enumeration {
                      enum auto {
                        description
                          "Automatically derive NAS-Identifier as:
                           <interface-name>-<hostname>.<mobility-domain>.";
                      }
                    }
                    type string {
                      length "1..253";
                      pattern '[a-zA-Z0-9_.:+-]+';
                    }
                  }
                  default auto;
                  description
                    "Override NAS-Identifier used for 802.11r.

                     Set to 'auto' to derive:
                     <interface-name>-<hostname>.<mobility-domain>.

                     This value should be unique per AP BSS and stable.";
                }
              }

              container dot11v {
                presence "Enable 802.11v BSS Transition Management";
                description
                  "Enable 802.11v BSS Transition Management.

                   Allows APs to suggest better APs to clients, improving
                   network-assisted roaming decisions.";

                leaf band-steering {
                  type boolean;
                  default true;
                  description
                    "Multi-Band Operation (MBO) band steering.

                     Signals band preferences to capable clients,
                     encouraging dual-band devices to prefer 5GHz
                     over 2.4GHz when signal quality permits.

                     Acts on a 2.4GHz access point whose SSID is also
                     served on 5 or 6GHz by this device: it defers
                     dual-band clients to that access point, and moves
                     the ones already connected.  On a 5 or 6GHz
                     access point the setting has no effect.

                     MBO steers clients via 802.11v BSS Transition
                     Management, hence its placement under dot11v;
                     enabling dot11v enables band steering by default.

                     Only meaningful when the same SSID is offered on
                     two or more bands (an access-point per radio); a
                     single-band BSS has no other band to steer toward.

                     Safe to leave enabled (default) - only activates
                     when both AP and client support MBO.";
                }
              }

              leaf okc {
                type boolean;
                default true;
                description
                  "Opportunistic Key Caching (OKC).

                   Reduces re-authentication time for roaming clients
                   that don't support 802.11r. The AP caches PMK from
                   previous associations and shares them with other APs
                   in the same mobility group.

                   Safe to leave enabled (default) - only activates when
                   both AP and client support it.";
              }
            }

            /* Operational state */

            container stations {
              list station {
                config false;
                key mac-address;
                description
                  "List of currently connected clients (stations).";

                leaf mac-address {
                  type yang:mac-address;
                  description "Client MAC address.";
                }

                leaf signal-strength {
                  type int16;
                  units "dBm";
                  description "Client signal strength in dBm.";
                }

                leaf connected-time {
                  type uint32;
                  units "seconds";
                  description "Time since client connected, in seconds.";
                }

                leaf rx-packets {
                  type yang:counter64;
                  description "Packets received from this client.";
                }

                leaf tx-packets {
                  type yang:counter64;
                  description "Packets transmitted to this client.";
                }

                leaf rx-bytes {
                  type yang:counter64;
                  units "octets";
                  description "Bytes received from this client.";
                }

                leaf tx-bytes {
                  type yang:counter64;
                  units "octets";
                  description "Bytes transmitted to this client.";
                }

                leaf rx-speed {
                  type uint32;
                  units "100 kbps";
                  description
                    "Last received data rate from this client in 100 kbps.

                     Examples:
                     - 10 = 1 Mbps
                     - 65 = 6.5 Mbps
                     - 866 = 86.6 Mbps";
                }

                leaf tx-speed {
                  type uint32;
                  units "100 kbps";
                  description
                    "Last transmitted data rate to this client in 100 kbps.

                     Examples:
                     - 10 = 1 Mbps
                     - 65 = 6.5 Mbps
                     - 866 = 86.6 Mbps";
                }
              }
            }
          }
        }

        case mesh-point {
          container mesh-point {
            presence "Configure 802.11s mesh point mode";

            must "/iehw:hardware/iehw:component[iehw:name = current()/../radio]/ih:wifi-radio/ih:band" {
              error-message "Parent radio must have 'band' configured for mesh mode";
            }

            must "/iehw:hardware/iehw:component[iehw:name = current()/../radio]/ih:wifi-radio/ih:channel" {
              error-message "Parent radio must have 'channel' configured for mesh mode";
            }

            must "/iehw:hardware/ih:wifi/ih:country-code != '00'" {
              error-message "Set the Wi-Fi country code (hardware wifi country-code) before configuring a mesh point, the world domain '00' is not allowed.";
            }

            must "not(/if:interfaces/if:interface[wifi/access-point][wifi/radio = current()/../radio])" {
              error-message "Mesh point and access point cannot coexist on the same radio";
            }

            description
              "802.11s Mesh Point mode configuration.

               In mesh mode, the interface creates a peer-to-peer mesh
               link with other mesh points sharing the same mesh ID.

               Only one mesh point interface is allowed per radio.
               Mesh point and access point cannot share the same radio.

               Example use case: Wireless backhaul between APs.";

            leaf mesh-id {
              type string {
                length "1..32";
                pattern '[^\x00-\x1f\x22\x5c\x7f]*' {
                  error-message "Mesh ID must not contain control characters, double quotes, or backslashes.";
                }
              }
              mandatory true;
              description
                "Mesh network identifier.

                 All mesh points that should form a mesh network
                 must use the same mesh ID.";
            }

            leaf forwarding {
              type boolean;
              default true;
              description
                "Enable layer-2 mesh forwarding (mesh_fwding).

                 When true, the mesh interface can be added to a Linux
                 bridge for transparent L2 connectivity (mesh portal).

                 When false, only locally destined traffic is received.";
            }

            container security {
              description
                "Mesh security configuration.

                 All mesh links use WPA3-SAE encryption.";

              leaf secret {
                type ks:central-symmetric-key-ref;
                mandatory true;
                description
                  "Pre-shared key (PSK) reference for SAE mesh.

                   References a symmetric key in the keystore.
                   All mesh points in the same mesh must share
                   the same key.";
              }
            }

            /* Operational state */

            container peers {
              list peer {
                config false;
                key mac-address;
                description
                  "List of currently connected mesh peers.";

                leaf mac-address {
                  type yang:mac-address;
                  description "Mesh peer MAC address.";
                }

                leaf signal-strength {
                  type int16;
                  units "dBm";
                  description "Peer signal strength in dBm.";
                }

                leaf connected-time {
                  type uint32;
                  units "seconds";
                  description "Time since peer connected, in seconds.";
                }

                leaf rx-packets {
                  type yang:counter64;
                  description "Packets received from this peer.";
                }

                leaf tx-packets {
                  type yang:counter64;
                  description "Packets transmitted to this peer.";
                }

                leaf rx-bytes {
                  type yang:counter64;
                  units "octets";
                  description "Bytes received from this peer.";
                }

                leaf tx-bytes {
                  type yang:counter64;
                  units "octets";
                  description "Bytes transmitted to this peer.";
                }

                leaf rx-speed {
                  type uint32;
                  units "100 kbps";
                  description
                    "Last received data rate from this peer in 100 kbps.";
                }

                leaf tx-speed {
                  type uint32;
                  units "100 kbps";
                  description
                    "Last transmitted data rate to this peer in 100 kbps.";
                }
              }
            }
          }
        }

        case wds-link {
          container wds-link {
            presence "Configure a 4-address WDS port of a local access point";

            description
              "Bridge port for one 4-address (WDS) station on an access
               point of this device.

               The access point binds the station with the given MAC
               address to this interface.  Add the interface to the access
               point's bridge and configure VLANs like for any other port;
               one wds-link per repeater or remote bridge.  The port is up
               while the station is associated.

               Give the access point an SSID and secret of its own, for
               the WDS links only: a station that knows them and uses
               the MAC address below is bound to this port, with every
               VLAN the port carries.

               The interface uses the access point's radio and MAC
               address.";

            must "not(../../custom-phys-address/*)" {
              error-message "A wds-link uses the MAC address of its access point";
            }

            must "not(../radio)" {
              error-message "A wds-link uses the radio of its access point, do not set radio";
            }

            leaf access-point {
              type leafref {
                path "/if:interfaces/if:interface/if:name";
              }
              mandatory true;
              must "/if:interfaces/if:interface[if:name = current()]/wifi/access-point" {
                error-message "wds-link must reference an access point interface on this device";
              }
              description
                "Access point interface this port belongs to.";
            }

            leaf peer-address {
              type yang:mac-address;
              mandatory true;
              must "count(/if:interfaces/if:interface[wifi/wds-link/access-point = current()/../access-point][wifi/wds-link/peer-address = current()]) = 1" {
                error-message "Only one wds-link per station on an access point";
              }
              description
                "MAC address of the 4-address station bound to this port.";
            }

            /* Operational state */

            leaf connected {
              config false;
              type boolean;
              description
                "True while the station is associated and bound to this
                 port.";
            }

            leaf signal-strength {
              config false;
              type int16;
              units "dBm";
              description
                "Signal strength of the station in dBm.  Only present
                 while connected.";
            }

            leaf rx-speed {
              config false;
              type uint32;
              units "100 kbps";
              description
                "Last received data rate from the station in 100 kbps.
                 Only present while connected.";
            }

            leaf tx-speed {
              config false;
              type uint32;
              units "100 kbps";
              description
                "Last transmitted data rate to the station in 100 kbps.
                 Only present while connected.";
            }
          }
        }
      }
    }
  }
}
