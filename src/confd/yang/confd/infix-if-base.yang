submodule infix-if-base {
  yang-version 1.1;
  belongs-to infix-interfaces {
    prefix infix-if;
  }

  import ietf-interfaces {
    prefix if;
  }

  organization "KernelKit";
  contact      "kernelkit@googlegroups.com";
  description  "Linux link aggregates (lag) for ietf-interfaces.";

  revision 2023-08-21 {
    description "Initial revision.";
    reference "internal";
  }

  /*
   * Data Nodes
   */

  augment "/if:interfaces/if:interface" {
    description "Augments the interface model with mutually exclusive guards.";

    choice port {
      description "An interface can only be member of either a bridge or a link aggregate.";
    }
  }
}
