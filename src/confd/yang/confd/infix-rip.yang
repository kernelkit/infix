module infix-rip {
  yang-version 1.1;
  namespace "urn:infix:rip:ns:yang:1.0";
  prefix infix-rip;

  import ietf-routing {
    prefix rt;
  }
  import ietf-rip {
    prefix rip;
  }
  import ietf-inet-types {
    prefix inet;
  }
  import ietf-interfaces {
    prefix if;
  }
  import infix-routing {
    prefix infix-rt;
  }

  organization "KernelKit";
  contact      "kernelkit@googlegroups.com";
  description  "Deviations and augments for ietf-rip.";

  revision 2026-10-30 {
    description "The route tables are no longer operational data, the new
                 get-routes action reads them from the daemon on request.";
    reference "internal";
  }

  revision 2026-10-26 {
    description "Initial revision, the ietf-rip deviations and augments from
                 infix-routing.";
    reference "internal";
  }

  /* RIP */
  /* RIP features not supported in Infix/FRR */
  deviation "/rt:routing/rt:control-plane-protocols/rt:control-plane-protocol/rip:rip/rip:originate-default-route/rip:route-policy" {
    deviate not-supported;
    description "Route policies are not supported.";
  }

  deviation "/rt:routing/rt:control-plane-protocols/rt:control-plane-protocol/rip:rip/rip:triggered-update-threshold" {
    deviate not-supported;
    description "Triggered update threshold is not supported in FRR.";
  }

  deviation "/rt:routing/rt:control-plane-protocols/rt:control-plane-protocol/rip:rip/rip:maximum-paths" {
    deviate not-supported;
    description "Maximum paths configuration is not supported in FRR.";
  }

  deviation "/rt:routing/rt:control-plane-protocols/rt:control-plane-protocol/rip:rip/rip:output-delay" {
    deviate not-supported;
    description "Output delay configuration is not supported in FRR.";
  }

  deviation "/rt:routing/rt:control-plane-protocols/rt:control-plane-protocol/rip:rip/rip:distribute-list" {
    deviate not-supported;
    description "Distribute lists are not supported.";
  }

  deviation "/rt:routing/rt:control-plane-protocols/rt:control-plane-protocol/rip:rip/rip:redistribute" {
    deviate not-supported;
    description "Use Infix-specific redistribute container instead.";
  }

  /* RIP Interface features not supported */
  deviation "/rt:routing/rt:control-plane-protocols/rt:control-plane-protocol/rip:rip/rip:interfaces/rip:interface/rip:authentication" {
    deviate not-supported;
    description "RIP authentication is not supported.";
  }

  deviation "/rt:routing/rt:control-plane-protocols/rt:control-plane-protocol/rip:rip/rip:interfaces/rip:interface/rip:bfd" {
    deviate not-supported;
    description "BFD support for RIP is not available in FRR.";
  }

  deviation "/rt:routing/rt:control-plane-protocols/rt:control-plane-protocol/rip:rip/rip:interfaces/rip:interface/rip:no-listen" {
    deviate not-supported;
    description "No-listen mode is not supported.";
  }

  deviation "/rt:routing/rt:control-plane-protocols/rt:control-plane-protocol/rip:rip/rip:interfaces/rip:interface/rip:originate-default-route" {
    deviate not-supported;
    description "Per-interface default route origination is not supported.";
  }

  deviation "/rt:routing/rt:control-plane-protocols/rt:control-plane-protocol/rip:rip/rip:interfaces/rip:interface/rip:summary-address" {
    deviate not-supported;
    description "Summary addresses are not supported.";
  }

  deviation "/rt:routing/rt:control-plane-protocols/rt:control-plane-protocol/rip:rip/rip:interfaces/rip:interface/rip:timers" {
    deviate not-supported;
    description "Per-interface timers are not supported in FRR.";
  }

  /* RIP Operational state not supported */
  deviation "/rt:routing/rt:control-plane-protocols/rt:control-plane-protocol/rip:rip/rip:interfaces/rip:interface/rip:statistics" {
    deviate not-supported;
    description "Per-interface statistics are not collected.";
  }

  deviation "/rt:routing/rt:control-plane-protocols/rt:control-plane-protocol/rip:rip/rip:next-triggered-update" {
    deviate not-supported;
    description "Next triggered update information is not available.";
  }

  deviation "/rt:routing/rt:control-plane-protocols/rt:control-plane-protocol/rip:rip/rip:num-of-routes" {
    deviate not-supported;
    description "Number of routes is not tracked separately.";
  }

  deviation "/rt:routing/rt:control-plane-protocols/rt:control-plane-protocol/rip:rip/rip:statistics" {
    deviate not-supported;
    description "Global statistics are not collected.";
  }

  /* The route tables are read when asked, see the get-routes action. */
  deviation "/rt:routing/rt:control-plane-protocols/rt:control-plane-protocol/rip:rip/rip:ipv4/rip:routes" {
    deviate not-supported;
  }

  deviation "/rt:routing/rt:control-plane-protocols/rt:control-plane-protocol/rip:rip/rip:ipv6/rip:routes" {
    deviate not-supported;
  }

  augment "/rt:routing/rt:control-plane-protocols/rt:control-plane-protocol/rip:rip" {
    description
      "Read the RIP routing table on request.";

    action get-routes {
      description
        "List the routes the RIP instance has learned.

         The route table is not operational data, this action reads it
         from the daemon when asked.  The routes RIP has installed are
         also in the RIB under ietf-routing.";

      output {
        list route {
          key "prefix";
          description "A route RIP has learned.";

          leaf prefix {
            type inet:ip-prefix;
            description "Destination prefix.";
          }

          leaf next-hop {
            type inet:ip-address;
            description "Next hop address.";
          }

          leaf interface {
            type if:interface-ref;
            description "The interface that the route uses.";
          }

          uses rip:route-attributes;
        }
      }
    }
  }

  /* RIP RPC */
  deviation "/rip:clear-rip-route" {
    deviate not-supported;
    description "Clear RIP route RPC is not supported.";
  }

  /* RIP Augmentations */
  augment "/rt:routing/rt:control-plane-protocols/rt:control-plane-protocol/rip:rip" {
    description "Infix-specific redistribute container for RIP.
                 The standard ietf-rip redistribute container has complex protocol-specific
                 lists (bgp, isis, ospfv2, etc.), but Infix uses a simpler model similar to OSPF.";
    container redistribute {
      list redistribute {
        key "protocol";
        description "Redistribute protocols into RIP";
        leaf protocol {
          type infix-rt:infix-distribute-protocol;
          description "Set protocol to redistribute";
        }
      }
    }
  }

  augment "/rt:routing/rt:control-plane-protocols/rt:control-plane-protocol/rip:rip" {
    description "Add support for configurable RIP debug logging.
                 Allows users to enable specific RIP debug categories for troubleshooting.
                 All debug options default to disabled to prevent log flooding in
                 production environments.";
    container debug {
      description "RIP debug logging configuration";
      leaf events {
        type boolean;
        default false;
        description "Enable RIP events debug messages (sending/receiving packets, timers, interface changes)";
      }
      leaf packet {
        type boolean;
        default false;
        description "Enable detailed RIP packet debug messages (packet dumps with origin and port)";
      }
      leaf kernel {
        type boolean;
        default false;
        description "Enable kernel routing table debug messages (route add/delete, interface updates)";
      }
    }
  }

  /* Add send/receive version control per RIP interface
   * The standard ietf-rip model doesn't include version control,
   * but FRR supports this and it's useful for controlling RIP protocol versions
   * on a per-interface basis (e.g., for NBMA links or mixed networks).
   */
  augment "/rt:routing/rt:control-plane-protocols/rt:control-plane-protocol/"
        + "rip:rip/rip:interfaces/rip:interface" {
    when "derived-from-or-self(../../../rt:type, 'infix-rt:ripv2')" {
      description
        "This augmentation is only valid for RIPv2.";
    }
    description
      "Infix extension to add RIP version control per interface.";

    leaf send-version {
      type enumeration {
        enum "1" {
          description "Send RIPv1 packets";
        }
        enum "2" {
          description "Send RIPv2 packets";
        }
        enum "1-2" {
          description "Send both RIPv1 and RIPv2 packets";
        }
      }
      description
        "RIP version to send on this interface. If not configured, FRR defaults to version 2.";
    }

    leaf receive-version {
      type enumeration {
        enum "1" {
          description "Receive RIPv1 packets";
        }
        enum "2" {
          description "Receive RIPv2 packets";
        }
        enum "1-2" {
          description "Receive both RIPv1 and RIPv2 packets";
        }
      }
      description
        "RIP version to receive on this interface. If not configured, FRR defaults to version 2.";
    }
  }
}
