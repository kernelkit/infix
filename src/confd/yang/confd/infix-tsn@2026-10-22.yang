module infix-tsn {
  yang-version 1.1;
  namespace "urn:infix:tsn:ns:yang:1.0";
  prefix infix-tsn;

  import ietf-interfaces {
    prefix if;
  }
  import ieee802-dot1dc-sched-if {
    prefix sched-if;
  }
  import ieee802-dot1q-sched {
    prefix sched;
  }

  organization "KernelKit";
  contact      "kernelkit@googlegroups.com";
  description  "Deviations to the IEEE 802.1DC time-sensitive networking
     modules.

     The scheduled traffic capability leaves are read-only here, as the
     standard allows, and the constraints that compare configuration
     against them are removed: a comparison with a leaf the operator
     cannot set fails on every interface, configured or not.  The list
     is checked against what the port supports when it is applied.

     A gate control list takes effect when it is committed, so the
     config-change trigger and the gate states to hold before a list
     starts are not supported.  Frame preemption is not supported
     either, which leaves set-gate-states as the one gate operation.";

  revision 2026-10-22 {
    description "Initial revision.";
    reference "internal";
  }

  deviation "/if:interfaces/if:interface/sched-if:gate-parameter-table"
          + "/sched-if:supported-list-max" {
    deviate add {
      config false;
    }
  }

  deviation "/if:interfaces/if:interface/sched-if:gate-parameter-table"
          + "/sched-if:supported-cycle-max" {
    deviate add {
      config false;
    }
  }

  deviation "/if:interfaces/if:interface/sched-if:gate-parameter-table"
          + "/sched-if:supported-interval-max" {
    deviate add {
      config false;
    }
  }

  deviation "/if:interfaces/if:interface/sched-if:gate-parameter-table"
          + "/sched-if:admin-control-list" {
    deviate delete {
      must "(count(./gate-control-entry) <= ../supported-list-max)";
    }
  }

  deviation "/if:interfaces/if:interface/sched-if:gate-parameter-table"
          + "/sched-if:oper-control-list" {
    deviate delete {
      must "(count(./gate-control-entry) <= ../supported-list-max)";
    }
  }

  deviation "/if:interfaces/if:interface/sched-if:gate-parameter-table"
          + "/sched-if:admin-control-list/sched-if:gate-control-entry"
          + "/sched-if:time-interval-value" {
    deviate delete {
      must "(. <= ../../../supported-interval-max )";
    }
  }

  deviation "/if:interfaces/if:interface/sched-if:gate-parameter-table"
          + "/sched-if:oper-control-list/sched-if:gate-control-entry"
          + "/sched-if:time-interval-value" {
    deviate delete {
      must "(. <= ../../../supported-interval-max )";
    }
  }

  deviation "/if:interfaces/if:interface/sched-if:gate-parameter-table"
          + "/sched-if:admin-cycle-time" {
    deviate delete {
      must "(./numerator div ./denominator <= "
         + "../supported-cycle-max/numerator div "
         + "../supported-cycle-max/denominator )";
    }
  }

  deviation "/if:interfaces/if:interface/sched-if:gate-parameter-table"
          + "/sched-if:admin-gate-states" {
    deviate not-supported;
  }

  deviation "/if:interfaces/if:interface/sched-if:gate-parameter-table"
          + "/sched-if:config-change" {
    deviate not-supported;
  }

  deviation "/if:interfaces/if:interface/sched-if:gate-parameter-table"
          + "/sched-if:admin-control-list/sched-if:gate-control-entry"
          + "/sched-if:operation-name" {
    deviate add {
      must "derived-from-or-self(., 'sched:set-gate-states')" {
        error-message "Only set-gate-states is supported.";
      }
    }
  }
}
