module infix-services {
  yang-version 1.1;
  namespace "urn:ietf:params:xml:ns:yang:infix-services";
  prefix infix-svc;

  import ietf-interfaces {
    prefix if;
  }
  import ietf-inet-types {
    prefix inet;
    reference
      "RFC 6991: Common YANG Data Types";
  }
  import infix-crypto-types {
    prefix infix-ct;
    reference
      "RFC 9640: YANG Data Types and Groupings for Cryptography";
  }
  import ietf-yang-types {
    prefix yang;
  }
  import infix-system {
    prefix infix-sys;
  }

  import ietf-keystore {
    prefix ks;
  }

  organization "KernelKit";
  contact      "kernelkit@googlegroups.com";
  description  "Infix services, generic.";

  revision 2026-10-27 {
    description "Add web/restconf/rate-limit, how fast another host may
                 send RESTCONF requests.";
    reference "internal";
  }
  revision 2026-09-24 {
    description "Add netconf container to ssh, NETCONF is now an SSH subsystem
                 served by the SSH daemon on port 830.";
    reference "internal";
  }
  revision 2026-09-18 {
    description "Add TFTP server.";
    reference "internal";
  }
  revision 2026-06-17 {
    description "Add web-ui feature, advertised when the web management
                 interface (webui) is built into the image.";
    reference "internal";
  }
  revision 2026-03-20 {
    description "Add hostname leaf to mdns container for avahi host-name override.
                 Add neighbors container to mdns for mDNS-SD neighbor table.
                 Add certificate leaf to web container for TLS keystore reference.";
    reference "internal";
  }
  revision 2025-12-10 {
    description "Adapt to changes in final version of ietf-keystore";
    reference "internal";
  }
  revision 2024-12-03 {
    description "Add support for SSH server configuration";
    reference "internal";
  }
  revision 2024-12-02 {
    description "Expand mdns options: domain, allow/deny interfaces, reflector.";
    reference "internal";
  }

  revision 2024-06-08 {
    description "Add support for RESTCONF enable/disable as a web service.";
    reference "internal";
  }
  revision 2024-05-30 {
    description "Add support for RESTCONF enable/disable as a web service.";
    reference "internal";
  }
  revision 2024-04-08 {
    description "Initial support for web services.";
    reference "internal";
  }
  revision 2023-10-16 {
    description "Drop SSDP support, mDNS-SD is now available in Windows 10.";
    reference "internal";
  }
  revision 2023-08-22 {
    description "Initial revision, add SSDP and mDNS-SD enable/disable only.";
    reference "internal";
  }

  feature web-ui {
    description "The web management interface (webui) is an optional build-time
                 feature in Infix.  Advertised when it is built; it gates no
                 data nodes — the /web service tree (including restconf) is
                 present regardless, so the feature is a pure capability flag.";
  }

  /*
   * Data nodes
   */

  container mdns {
    description "Advertise system and services over mDNS-SD, IPv4 and IPv6.";

    leaf enabled {
      description "Globally enable or disable mDNS/SD on all interfaces.";
      type boolean;
    }

    leaf domain {
      description "LAN domain name to register host name and services in.

                   Most common is .local, but some also use .lan, or .office,
                   usually this setting can be left as-is.";
      default "local";
      type inet:domain-name;
    }

    leaf hostname {
      description "Hostname for mDNS A/AAAA records (avahi host-name setting).

                   When not set the default is the build-time branding hostname.
                   Supports the same format specifiers as /system/hostname:
                     %h  Default hostname (DEFAULT_HOSTNAME from os-release)
                     %i  OS ID from os-release
                     %m  Last three octets of base MAC (e.g. c0-ff-ee)";
      type infix-sys:hostname;
      default "%h";
    }

    container interfaces {
      description "Filter interfaces to act on.";

      leaf-list allow {
        description "Enabled on interfaces, can be combined with deny-interfaces.

                     By default all, except loopback and point-to-point links.";
        type if:interface-ref;
      }

      leaf-list deny {
        description "Disabled on interfaces (always wins).

                     Other not specified interfaces will be used, except loopback
                     and point-to-point, unless combined with allow-interfaces.

                     This option takes precedence over allow-interfaces.";
        type if:interface-ref;
      }
    }

    container reflector {
      description "Reflect incoming mDNS requests to local interfaces.";

      leaf enabled {
        description "Enable mDNS reflector on local interfaces.";
        type boolean;
      }

      leaf-list service-filter {
        description "Filter mDNS service names to reflect.

                     Example, for AirPlay and AirTunes, use:

                       - _airplay._tcp.local
                       - _raop._tcp.local

                     For AirPrint use:

                       - _printer._tcp.local
                       - _ipp._tcp.local
                       - _pdl-datastream._tcp.local

                     By default all services are reflected.";
        type string;
      }
    }

    container neighbors {
      config false;
      description "mDNS neighbor table populated by statd on avahi D-Bus events.
                   All DNS-SD hosts are included; tools that need to identify Infix
                   devices check for 'vv=1' in the txt leaf-list themselves.
                   Addresses and TXT records are stored in raw form from avahi.";

      list neighbor {
        key "hostname";
        description "A DNS-SD host discovered via avahi service browsing.";

        leaf hostname {
          type string;
          description "mDNS hostname as reported by avahi, e.g. 'infix-2.local'.";
        }

        leaf-list address {
          type inet:ip-address;
          description "All addresses reported by avahi for this host.
                       Loopback (127.x/::1) addresses are excluded.";
        }

        leaf last-seen {
          type yang:date-and-time;
          description "Timestamp of the most recent avahi resolver event for this host.";
        }

        list service {
          key "name";
          description "DNS-SD services advertised by this neighbor.";

          leaf name {
            type string;
            description "Service instance name as announced, e.g. 'infix-2 Web'.";
          }

          leaf type {
            type string;
            description "Raw mDNS service type, e.g. '_https._tcp', '_ssh._tcp'.";
          }

          leaf port {
            type inet:port-number;
            description "TCP or UDP port number for this service.";
          }

          leaf-list txt {
            type string;
            description "Raw DNS-SD TXT record strings for this service instance,
                         e.g. 'vv=1', 'product=Infix', 'ov=25.01.0'.
                         Stored verbatim; callers split on '=' to extract key-value pairs.";
          }
        }
      }
    }
  }
  container ssh {
    description "Configuration for the SSH daemon";
    leaf enabled {
      description "Enable or disable SSH daemon";
      type boolean;
      must ". = 'false' or (count(../listen) > 0 and count(../hostkey) > 0)" {
        error-message "Must be at least one listen address and a private key.";
      }
    }

    leaf-list hostkey {
      description "Reference to asymmetric key in central keystore.

             The hostkey can be shared with NETCONF, by default 'genkey' is used.";
      must "not(deref(.)/../ks:public-key-format) or "
        + "(derived-from-or-self(deref(.)/../ks:public-key-format,  'infix-ct:ssh-public-key-format') and"
        + "derived-from-or-self(deref(.)/../ks:private-key-format,  'infix-ct:rsa-private-key-format'))" {
        error-message "Only RSA hostkeys are supported.";
      }
      type ks:central-asymmetric-key-ref;
    }

    list listen {
      key name;
      description "List of IP addresses and ports the SSH daemon should listen on.

         Each entry represents a unique listening socket configuration
         that allows incoming SSH connections. Multiple entries can be
         configured to listen on different addresses or ports.";
      leaf name {
        description "A unique identifier for this listening configuration.

           This name helps administrators distinguish between multiple
           listening configurations. It can reflect the purpose or
           network segment of the listener, e.g., 'management',
           'internal', or 'public'.";
        type string;
      }

      leaf address {
        description "Local IP address to listen on for inbound SSH connections.

           INADDR_ANY (0.0.0.0) or INADDR6_ANY (0:0:0:0:0:0:0:0 a.k.a. ::) MUST be
           used when the server is to listen on all IPv4 or
           IPv6 addresses, respectively.";
        type inet:ip-address;
      }
      leaf port {
        description "Local port for SSH daemon to listen on.";
        type inet:port-number;
      }
      must "port and address" {
        error-message "Both address and port must be configured";
      }
    }

    container netconf {
      description "NETCONF over SSH, RFC 6242, on port 830.

         In the default build the SSH daemon serves it, on the same
         addresses as the listen entries above and as the 'netconf'
         subsystem on all other SSH ports.  It keeps the SSH daemon
         running on port 830 also when SSH logins are disabled.  Builds
         where netopeer2-server has its own SSH transport configure the
         endpoint in ietf-netconf-server.";

      leaf enabled {
        description "Enable or disable the NETCONF server.";
        type boolean;
        default true;
      }
    }
  }

  container web {
    description "Web services";

    leaf certificate {
      description "Reference to asymmetric key in central keystore with an
                   associated certificate. By default 'gencert' is used.";
      type ks:central-asymmetric-key-ref;
    }

    leaf enabled {
      description "Enable or disable on all web services.

                   Enabling this setting activates a web proxy server reponsible
                   for routing requests to other web applications, as well as it
                   redirecting all insecure HTTP requests to HTTPS.

                   Disabling this setting disables the web proxy server and all
                   other services/applications that run behind it.";
      type boolean;
    }

    container console {
      description "Web console interface.";

      leaf enabled {
        description "Enable or disable web console interface on port 7681.";
        type boolean;
      }
    }

    container netbrowse {
      description "mDNS Network Browser.";

      leaf enabled {
        description "Enable or disable mDNS Network Browser at https://network.local.";
        type boolean;
      }
    }

    container restconf {
      description "IETF RESTCONF Server.";

      leaf enabled {
        description "Enable or disable RESTCONF server.";
        type boolean;
      }

      container rate-limit {
        description
          "Limit how fast another host may send RESTCONF requests.

           RESTCONF checks the password on every request, so this slows
           down password guessing.  Each host is limited on its own, and
           requests from the device itself, e.g., the WebUI, are never
           limited.  A host over the limit gets HTTP 429.";

        leaf enabled {
          description "Limit how fast another host may send requests.";
          type boolean;
          default true;
        }

        leaf rate {
          description "Requests a second a host may send over time.";
          type uint16 {
            range "1..10000";
          }
          units "requests/second";
          default 10;
        }

        leaf burst {
          description
            "Requests a host may send at once, above the rate.

             A client that downloads the YANG modules when it connects
             sends a burst of a few hundred requests.";
          type uint16 {
            range "0..10000";
          }
          default 200;
        }
      }
    }
  }

  container tftp {
    description "Read-only TFTP server for network boot and provisioning.";

    leaf enabled {
      description "Enable or disable the TFTP server.";
      type boolean;
      default false;
    }

    leaf root {
      description "Directory to serve files from, below /var/lib/tftpboot or
                   /media.  Requests for files outside it are refused, and
                   only world-readable files are served.";
      type string {
        pattern '(/var/lib/tftpboot|/media/[^/.\p{Cc}][^/\p{Cc}]*)(/[^/.\p{Cc}][^/\p{Cc}]*)*';
      }
      default "/var/lib/tftpboot";
    }

    leaf-list interface {
      description "Serve TFTP on these interfaces only, default all.";
      type if:interface-ref;
    }

    leaf client-directory {
      description "Look for files in a subdirectory of the root named after
                   the client before falling back to the root itself.  Used
                   for per-device files, e.g., configuration.";
      type enumeration {
        enum ip {
          description "Client IP address, e.g., 192.168.2.10";
        }
        enum mac {
          description "Client MAC address, lower case with dashes,
                       e.g., 00-11-22-33-44-55";
        }
      }
    }

    container files {
      description "Files served, i.e., world-readable files below the root.";
      config false;

      list file {
        key name;

        leaf name {
          description "File name, relative to the TFTP root.";
          type string;
        }

        leaf size {
          type uint64;
          units "bytes";
        }

        leaf modified {
          type yang:date-and-time;
        }
      }
    }
  }
}
