module infix-keystore {
  yang-version 1.1;
  namespace "urn:infix:keystore:ns:yang:1.0";
  prefix infix-ks;
  import ietf-keystore {
    prefix ks;
  }
  import infix-crypto-types {
    prefix infix-ct;
  }

  revision 2026-09-24 {
    description "Constrain the character set of asymmetric-key and
                 certificate names.";
    reference "internal";
  }

  revision 2025-12-17 {
    description "Add WireGuard support, see infix-crypto-types.yang";
  }
  revision 2025-12-10 {
    description "Adapt to changes in final version of ietf-keystore";
  }
  revision 2025-06-17 {
    description "Add Wi-Fi secrets support";
  }
  revision 2025-02-04 {
    description "Initial";
  }

  deviation "/ks:keystore/ks:asymmetric-keys/ks:asymmetric-key/ks:name" {
    deviate replace {
      type string {
        pattern '[a-zA-Z0-9_][a-zA-Z0-9_.:+@-]*';
      }
    }
    description "Key names are plain identifiers.";
  }

  deviation "/ks:keystore/ks:asymmetric-keys/ks:asymmetric-key/ks:certificates/ks:certificate/ks:name" {
    deviate replace {
      type string {
        pattern '[a-zA-Z0-9_][a-zA-Z0-9_.:+@-]*';
      }
    }
    description "Certificate names are plain identifiers.";
  }
}
