submodule infix-system-software {
  yang-version 1.1;
  belongs-to infix-system {
    prefix ixsys;
  }

  import ietf-yang-types {
    prefix yang;
  }

  import ietf-netconf-acm {
    prefix nacm;
  }

  import ietf-system {
    prefix sys;
  }

  import infix-schedule {
    prefix infix-schedule;
  }

  organization "KernelKit";
  contact      "kernelkit@googlegroups.com";
  description  "Software status and upgrade.";

  revision 2026-10-01 {
    description "Add the check-update RPC, and bundle-url to the update
                 operational data.";
    reference "Internal";
  }
  revision 2026-09-07 {
    description "Add unattended-update config, triggered from a referenced
                 schedule.  Lift update-url to the shared software container
                 so check-update and unattended-update use one update source,
                 make it an RSS/Atom release feed, and make it mandatory,
                 supplied by factory-config.
                 Add allow-prerelease.
                 Use the infix-schedule scheduled-feature grouping for
                 check-update and unattended-update, enabled now defaults
                 to true.
                 Add the update container to the operational data: outcome
                 of the last update check or unattended update.";
    reference "Internal";
  }
  revision 2026-06-17 {
    description "Add check-update config, triggered from a referenced schedule";
    reference "Internal";
  }
  revision 2024-12-16 {
    description "Add boot-order operational data";
    reference "Internal";
  }
  revision 2023-06-27 {
    description "Initial revision.";
    reference "internal";
  }

  grouping rauc-stage-log {
    leaf datetime {
      type yang:date-and-time;
      description
        "The time of the event.";
    }

    leaf count {
      type uint32;
      description
        "The total number of occurrences of the event.";
    }
  }

  grouping boot-order {
    leaf-list boot-order {
        type enumeration {
          enum "primary";
          enum "secondary";
          enum "net";
        }
        ordered-by user;
        min-elements 1; // At least one value is required
        max-elements 3; // Ensure reasonable maximum size if needed
      }
  }
  grouping installer-state {
    leaf operation {
      type string;
      description
        "The current operation of the installer service.";
    }

    container progress {
      leaf percentage {
        type uint8 {
          range "0 .. 100";
        }
      }

      leaf message {
        type string;
      }
    }

    leaf last-error {
      type string;
      description
        "The last error encountered by the installer service.";
    }
  }
  augment "/sys:system" {
    container software {
      /* An augment may not add a mandatory node (update-url) unconditionally. */
      presence "Software management configured.";
      description "Software management configuration.";

      leaf update-url {
        type string;
        mandatory true;
        description "RSS/Atom feed of releases to follow.

           The newest entry decides the latest version.  Each entry links to
           its release page as '<base>/releases/tag/<tag>', and the bundle
           for this platform is fetched from
           '<base>/releases/download/<tag>/<image-id>-<tag>.pkg'.

           Set by the factory configuration, change it to follow a fork or
           a feed of your own.";
      }

      leaf allow-prerelease {
        type boolean;
        default false;
        description "Consider pre-releases when determining the latest version.

           Release candidates, alpha and beta builds are listed alongside
           finished releases in most feeds.  By default they are ignored, so
           only a final release is ever installed.";
      }

      container check-update {
        description "Automatic software update checks.

           Each occurrence of the referenced schedule checks update-url for
           a newer release and logs a notification if there is one.";

        uses infix-schedule:scheduled-feature;
      }

      container unattended-update {
        description "Unattended software updates.

           Each occurrence of the referenced schedule checks update-url for
           a newer release and installs it to the inactive slot exactly as
           a manual 'upgrade' would: the boot-order is flipped to activate
           it on the next reboot, and the running slot is kept as fallback.

           The 'reboot' leaf decides whether that reboot is automatic.";

        uses infix-schedule:scheduled-feature;

        leaf reboot {
          type enumeration {
            enum manual {
              description "Leave the reboot to the operator.";
            }
            enum immediate {
              description "Reboot right after a successful install.";
            }
          }
          default manual;
          description "What to do once a new release has been installed.";
        }
      }
    }
  }

  augment "/sys:system-state" {
    container software {
      description
        "Installed software information

        Determined by RAUC, which manages all software upgrades.";
      reference "https://rauc.io/";

      leaf compatible {
        type string;
        description
          "Platform identifier

          Software bundles' compatible attributes are matched against this
          one, to determine if they are compatible with one another.";
      }

      leaf variant {
        type string;
        description
          "Hardware variant

          Identifies the exact system type.";
      }

      leaf booted {
        type string;
        description
          "Slot from which the system was booted.";
      }
      uses boot-order;

      container installer {
        description
          "The current state of the software installer service.";

        uses installer-state;

        // TODO: Support sending notifications during bundle installation
        // notification state-changed {
        //   uses installer-state;
        // }
      }

      container update {
        description "Outcome of the last update check or unattended update.";

        leaf last-check {
          type yang:date-and-time;
          description "When the release feed was last queried.";
        }

        leaf latest {
          type string;
          description "Newest release the feed offered at the last check.

             Pre-releases are left out unless allow-prerelease is set.  Absent
             when the feed could not be read.";
        }

        leaf available {
          type boolean;
          description "True when latest is newer than the version that boots next.";
        }

        leaf release-url {
          type string;
          description "Release page of the latest release.";
        }

        leaf bundle-url {
          type string;
          description "Bundle for this platform, ready for install-bundle or 'upgrade'.";
        }

        leaf last-install {
          type yang:date-and-time;
          description "When an unattended update last installed a bundle.";
        }

        leaf installed {
          type string;
          description "Version installed by the last unattended update.";
        }

        leaf reboot-pending {
          type boolean;
          description "True when an installed update awaits a reboot.

             The slot that boots next holds another version than the running
             one.";
        }
      }

      list slot {
        key "name";
        description
          "Details the installed software and current state of a particular
          storage slot (partition).";

        leaf name {
          type string;
          description
            "RAUC's internal name for the slot, in <class>.<id> notation.";
        }

        leaf bootname {
          type string;
          description
            "Short name of the slot.";
        }

        leaf class {
          type string;
          description
            "Class of software compatible with the slot.";
        }

        leaf state {
          type string;
          description
            "The slot's state.";
        }

        container bundle {
          leaf compatible {
            type string;
            description
              "Platform identifier of the installed software image.";
          }

          leaf version {
            type string;
            description
              "Version of the installed software image.";
          }
        }

        leaf size {
          type uint64;
          description
            "Size, in bytes, of the installed software image.";
        }

        leaf sha256 {
          type string {
            pattern '[a-fA-F0-9]{64}';
          }
          description
            "Checksum of the installed software image.";
        }
        container installed {
          description
            "Logs the time of the last installation and the total number of
            updates to this slot.";

          uses rauc-stage-log;
        }

        container activated {
          description
            "Logs the first time the current slot was activated and the total
            number of activations.";
          uses rauc-stage-log;
        }
      }
    }
  }

  rpc install-bundle {
    nacm:default-deny-all;
     description
       "Upgrade the system's software by installing the specified bundle.";
     input {
       leaf url {
         type string;
         mandatory true;
         description
           "The location of the software bundle, specified as a Uniform
           Resource Locator (URL).  Currently supported protocols include
           FTP, HTTP(S) and SCP.";
       }
     }
  }
  rpc set-boot-order {
    nacm:default-deny-all;
    description
      "Set order of boot partitions";
    input {
      uses boot-order;
      must "count(boot-order[.='primary']) <= 1 and
            count(boot-order[.='secondary']) <= 1 and
            count(boot-order[.='net']) <= 1" {
        error-message "Not possible to have duplicate targets in boot order.";
      }
    }
  }

  rpc check-update {
    description "Check the release feed for a newer release now.

       The same check as a check-update schedule occurrence: the outcome
       is recorded in /system-state/software/update, and a notice is
       shown at login when a newer release is available.  Fails when no
       update-url is configured or the feed cannot be read.";
    output {
      leaf latest {
        type string;
        description "Newest release the feed offers.";
      }
      leaf available {
        type boolean;
        description "True when latest is newer than the version that boots next.";
      }
      leaf release-url {
        type string;
        description "Release page of the latest release.";
      }
      leaf bundle-url {
        type string;
        description "Bundle for this platform, ready for install-bundle or 'upgrade'.";
      }
    }
  }
}
