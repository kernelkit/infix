module infix-if-type {
  yang-version 1.1;
  namespace "urn:infix:types:ns:yang:1.0";
  prefix infixift;

  import iana-if-type {
    prefix ianaift;
  }

  organization "KernelKit";
  contact      "kernelkit@googlegroups.com";
  description  "Infix extensions to IANA interfaces types";

  revision 2026-10-11 {
    description "Add interface type modem for cellular wwan interfaces.";
    reference "internal";
  }

  revision 2026-10-03 {
    description "Add interface type pppoe.";
    reference "internal";
  }

  revision 2026-01-07 {
    description "Add interface type wifi and wireguard";
    reference "internal";
  }

  revision 2025-02-12 {
    description "Remove interface type etherlike.";
    reference "internal";
  }

  revision 2024-10-13 {
    description "Add new interface type dummy.";
    reference "internal";
  }

  revision 2024-01-29 {
    description "Add new interface type etherlike.";
    reference "internal";
  }

  revision 2023-08-21 {
    description "Add infix-inteface-type to reduce number of supported
                 interfaces.  The derived identities are based on both
                 this new identity and their parent iana-if-type.";
    reference "internal";
  }

  revision 2023-06-09 {
    description "Initial revision.";
    reference "internal";
  }

  /*
   * Features
   */

  feature modem {
    description "Cellular modem support is an optional build-time feature in Infix.";
  }

  feature wifi {
    description "Wi-Fi support is an optional build-time feature in Infix.";
  }

  feature ppp {
    description "PPP support is an optional build-time feature in Infix.";
  }

  /*
   * Identities
   */

  identity infix-interface-type {
    base ianaift:iana-interface-type;
    description "Subset of supported iana-if-types.";
  }

  identity bridge {
    base infix-interface-type;
    base ianaift:bridge;
    description "IEEE bridge interface.";
  }
  identity dummy {
    base infix-interface-type;
    base ianaift:other;
    description "Linux virtual interface that is always UP.  Useful for
                 stable loopback-style addresses, e.g., as a permanent
                 management address or OSPF router-ID source.";
  }
  identity ethernet {
    base infix-interface-type;
    base ianaift:ethernetCsmacd;
    description "Any Ethernet interfaces, regardless of speed, RFC 3635.";
    reference   "RFC 3635";
  }


  identity gre {
    base infix-interface-type;
    description "GRE tunnel interface.";
  }
  identity gretap {
    base infix-interface-type;
    description "GRETAP (Ethernet over GRE) tunnel interface.";
  }
  identity vxlan {
    base infix-interface-type;
    description "Virtual eXtensible LAN tunnel interface.";
  }
  identity wireguard {
    base infix-interface-type;
    description "WireGuard VPN tunnel interface.";
  }
  identity lag {
    base infix-interface-type;
    base ianaift:ieee8023adLag;
    description "IEEE link aggregate interface.";
  }
  identity loopback {
    base infix-interface-type;
    base ianaift:softwareLoopback;
    description "Linux loopback interface.";
  }
  identity other {
    base infix-interface-type;
    base ianaift:other;
    description "Other interface, i.e., unknown.";
  }
  identity veth {
    base infix-interface-type;
    base ianaift:ilan;
    description "Linux virtual Ethernet pair.";
  }
  identity vlan {
    base infix-interface-type;
    base ianaift:l2vlan;
    description "Layer 2 Virtual LAN using 802.1Q.";
  }
  identity pppoe {
    if-feature ppp;
    base infix-interface-type;
    base ianaift:ppp;
    description "PPP over Ethernet (PPPoE) client session.";
  }

  identity modem {
    if-feature modem;
    base infix-interface-type;
    description "Cellular modem (wwan) network interface.
                 Created by the kernel (cdc_mbim, qmi_wwan) when a USB modem
                 attaches. Interface names follow the kernel wwan subsystem
                 naming convention: wwan[0-9]+.";
  }

  identity wifi {
    if-feature wifi;
    base infix-interface-type;
    base ianaift:ieee80211;
    description "Wi-Fi (802.11) interface";
  }
}
