module infix-if-type {
  yang-version 1.1;
  namespace "urn:infix:types:ns:yang:1.0";
  prefix infixift;

  import iana-if-type {
    prefix ianaift;
  }

  organization "KernelKit";
  contact      "kernelkit@googlegroups.com";
  description  "Infix extensions to IANA interfaces types";

  revision 2023-06-09 {
    description "Initial revision.";
    reference "internal";
  }

  /*
   * Identities
   */

  identity veth {
    base ianaift:ilan;
    description "Linux virtual Ethernet pair.";
  }
}
