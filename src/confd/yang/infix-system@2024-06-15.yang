module infix-system {
  yang-version 1.1;
  namespace "urn:infix:system:ns:yang:1.0";
  prefix infix-sys;

  import ietf-system {
    prefix sys;
  }
  import iana-timezones {
    prefix iana-tz;
  }

  include infix-system-software;

  organization "KernelKit";
  contact      "kernelkit@googlegroups.com";
  description  "Infix augments and deviations to ietf-system.";

  revision 2024-06-15 {
    description "Merge infix-shell-types.yang to add shell-type identities.";
    reference "internal";
  }

  revision 2024-06-14 {
    description "Add support for format specifiers in hostname:
                   - %h default hostname from /etc/os-release
                   - %i value of ID from /etc/os-release
                   - %m last three octets of base MAC, e.g., c0-ff-ee

                 Add support for yescrypt and $factory$ in password.
                 The latter is a reserved string which is interpreted
                 as the device default password from the VPD EEPROM.";
    reference "internal";
  }

  revision 2024-04-12 {
    description "New type, infix:hostname, for /system/hostname (max 64 chars).";
    reference "internal";
  }

  revision 2024-02-29 {
    description "Mark infix-sys:motd as deprecated, to be replaced with type binary.";
    reference "internal";
  }

  revision 2023-10-19 {
    description "Change deviation for timezone-utc-offset from unsupported to Etc+/-HOUR
                - Unit is set to hours (tzdata compatibility)
                - Range is -12 .. 14";

    reference "internal";
  }

  revision 2023-08-15 {
    description "Add support for user login shell.

                 Update/add deviation specifications:
                  - timezone-name (use tz defs from iana-timezone.yang)
                  - timezone-utc-offset (updated path for 'not-supported')
                  - radius ('not-supported')
                  - dns-resolver port ('not-supported')
                  - authentication username (limit length and pattern)";
    reference "internal";
  }

  revision 2023-04-11 {
    description "Initial revision.";
    reference "internal";
  }

  /*
   * Identities
   */

  identity editor-type {
    description "Base identity from which specific editor types are derived.";
  }

  identity emacs {
    description "Micro Emacs clone (mg).";
    base editor-type;
  }
  identity nano {
    description "GNU Nano.";
    base editor-type;
  }
  identity vi {
    description "The classic UNIX Visual editor.";
    base editor-type;
  }

  identity shell-type {
    description "Base identity from which specific shell types are derived.";
  }

  identity bash {
    description "Bourne again shell (BASH), standard UNIX shell.";
    base shell-type;
  }
  identity clish {
    description "Dedicated switch/router shell, similar to Cisco/JunOS.";
    base shell-type;
  }
  identity sh {
    description "POSIX shell, the original plain UNIX shell.";
    base shell-type;
  }
  identity false {
    description "Shell login disabled, both console and SSH.";
    base shell-type;
  }

  /*
   * Typedefs
   */

  typedef crypt-hash {
    type string {
      pattern
        '$0$.*'
      + '|$1$[a-zA-Z0-9./]{1,8}$[a-zA-Z0-9./]{22}'
      + '|$5$(rounds=\d+$)?[a-zA-Z0-9./]{1,16}$[a-zA-Z0-9./]{43}'
      + '|$6$(rounds=\d+$)?[a-zA-Z0-9./]{1,16}$[a-zA-Z0-9./]{86}'
      + '|$y$[a-zA-Z0-9./]+$[a-zA-Z0-9./]{1,86}$[a-zA-Z0-9./]{43}'
      + '|$factory$.*';
    }
    description
        "This type is used to store passwords using a hash function.  It
         extends the IANA crypt-hash type to support yescrypt as well as
         a reserved string '$factory$', used for device-specific factory
         default hash.  It is up to the underlying system to define this
         further, one example is to use Vital Product Data (VPD), e.g.,
         an onboard EEPROM where a device hash is stored for the initial
         'admin' user.

         A value of this type matches one of the forms:

           $0$<clear text password>
           $<id>$<salt>$<password hash>
           $<id>$<parameter>$<salt>$<password hash>

         The '$0$' prefix signals that the value is clear text, and even
         though it is supported, it is *not* recommended!  When such a
         value is received it passes through multiple subsystems before
         a hash value is calculated and the string '$<id>$<salt>$' or
         $<id>$<parameter>$<salt>$ is prepended and the result is stored
         in the configuration data store.  The hash function used depend
         on end system requirements.

         When any other '$<id>$' prefix is received, the system store it
         'as is' in the configuration data store.

         When a server needs to verify a password given by a user, it
         finds the stored password hash string for that user, extracts
         the salt, and calculates the hash with the salt and given
         password as input.  If the calculated hash value is the same as
         the stored value, the password given by the client is accepted.

         This type defines the following supported hash functions:

           id | hash function | feature
           ---+---------------+-------------------
            1 | MD5           | crypt-hash-md5
            5 | SHA-256       | crypt-hash-sha-256
            6 | SHA-512       | crypt-hash-sha-512
            y | yescrypt      | crypt-hash-yescrypt";
    reference
        "IEEE Std 1003.1-2008 - crypt() function
         RFC 1321: The MD5 Message-Digest Algorithm
         FIPS.180-4.2012: Secure Hash Standard (SHS)";
  }

  typedef username {
    type string {
      pattern "[_a-zA-Z0-9][-._a-zA-Z0-9]*$?";
      length "1..256";
    }
  }

  typedef hostname {
    type string {
      pattern
          '('
        + '(([a-zA-Z0-9_]([a-zA-Z0-9\-_]){0,61})?[a-zA-Z0-9]\.)*'
        + '([a-zA-Z0-9_]([a-zA-Z0-9\-_]){0,61})?[a-zA-Z0-9]\.?'
        + '|%[him]'
        + ')'
        + '([a-zA-Z0-9\-_\.]|%[him])*';
      length "1..64";
    }
    description "Linux have the same restrictions as IETF, only shorter.
                 Format specifiers are for, default hostname, ID, and the
                 last three octets in base MAC, e.g., c0-ff-ee";
  }

  /*
   * Data nodes
   */

  augment "/sys:system" {
    description "Augment of ietf-system for modifying /etc/motd.";

    leaf motd {
      description "Legacy MotD (Message of the Day), shown after login.

                   Please note, this is obsolete!  When set it overrides the
                   'motd-banner' setting for backwards compatibility.

                   Instead, use 'motd-banner', which takes a base64 encoded
                   text file as an argument.  For CLI users, edit with the
                   'text-editor motd-banner' command.";
      status obsolete;      // Replaced with motd-banner (binary)
      type string;
    }

    // From openconfig-system, which also has login-banner (TODO)
    leaf motd-banner {
      description "Message of the Day (MotD), shown after SSH/console login.

                   Base64 encoded (binary) file contents for the system file
                   /etc/motd, displayed after SSH/console login.

                   They system may append additional standard information such
                   as the current system date and time, uptime, last login
                   timestamp, etc.";
      type binary;
    }

    leaf text-editor {
      description "Text editor to use in CLI for text-editor command.";
      type identityref {
        base editor-type;
      }
      default emacs;
    }
  }

  augment "/sys:system/sys:authentication/sys:user" {
    description "Augment of ietf-system to support setting login shell for users.";
    leaf shell {
      type identityref {
        base shell-type;
      }
      default false;
      description "Set UNIX login shell for user, default: none (security)";
    }
  }

  deviation "/sys:system/sys:hostname" {
    deviate replace {
      type infix-sys:hostname;
    }
    description "Linux hostname can only be max 64 charachters long.";
  }

  deviation "/sys:system/sys:clock/sys:timezone/sys:timezone-name/sys:timezone-name" {
    deviate replace {
      type iana-tz:iana-timezone;
    }
  }

  deviation "/sys:system/sys:clock/sys:timezone/sys:timezone-utc-offset/sys:timezone-utc-offset" {
    description "Timezone UTC offset should be set in hours, not minutes";
    deviate replace {
      type int16 {
        range "-12 .. 14";
      }
      units "hours";
    }
  }

  deviation "/sys:system/sys:radius" {
    deviate not-supported;
  }

  deviation "/sys:system/sys:dns-resolver/sys:server/sys:transport/sys:udp-and-tcp/sys:udp-and-tcp/sys:port" {
    deviate not-supported;
  }

  deviation "/sys:system/sys:authentication/sys:user/sys:name" {
    deviate replace {
      type infix-sys:username;
    }
  }

  deviation "/sys:system/sys:authentication/sys:user/sys:password" {
    description "Extended password hash, including missing types, and $factory$.";
    deviate replace {
      type infix-sys:crypt-hash;
    }
  }
}
