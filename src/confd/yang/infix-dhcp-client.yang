module infix-dhcp-client {
  yang-version 1.1;
  namespace "urn:ietf:params:xml:ns:yang:dhcp-client";
  prefix dhcp-client;

  import ietf-interfaces {
    prefix if;
  }
  import infix-dhcp-common {
    prefix dhcp;
  }

  contact      "kernelkit@googlegroups.com";
  description  "This module implements a DHCPv4 client";

  revision 2025-01-29 {
    description   "Consolidate DHCP options between client and server models.
                      - Rename option attribute 'name' -> 'id'
                      - Rename internal option type
                      - Rename options, e.g. ntpsrv -> ntp-server";
    reference     "internal";
  }
  revision 2024-09-20 {
    description   "Routes are installed in Frr (staticd), clarify preference
                   vs metric and adjust default preference 100 -> 5.";
    reference     "internal";
  }
  revision 2024-04-12 {
    description   "Adjust DHCP client hostname option, max 64 charachters.";
    reference     "internal";
  }
  revision 2024-01-30 {
    description   "Add DHCP client options, arping, and route preference.";
    reference     "internal";
  }
  revision 2023-05-22 {
    description   "Initial revision.";
    reference     "rfc2131 rfc7950";
  }

  /*
   * Typedefs
   */

  typedef route-preference {
    type uint32;
    description "This type is used for selecting route preference (distance).";
  }

  /*
   * Data Nodes
   */

  container dhcp-client {
    description
      "DHCPv4 client configuration";
    leaf enabled {
      type boolean;
      default "true";
      description "Globally enables the DHCP client function.";
    }
    list client-if {
      key "if-name";
      description "List of interfaces requesting DHCPv4 configuration.";
      leaf if-name {
        type if:interface-ref;
        mandatory true;
        description "Name of the interface.";
      }
      leaf enabled {
        type boolean;
        default "true";
        description "Enable DHCP client for this interface.";
      }
      leaf client-id {
        type string;
        description "Optional Client ID, option 61, default: MAC address.";
      }
      leaf arping {
        type boolean;
        default "true";
        description "ARP for lease to check for IP address collisions (slow).";
      }
      list option {
        key "id";
        description
          "List of DHCP options to request (and accept).  The default is an
           empty list, meaning all supported options.  To restrict the
           client to only get IP address and default route, set this to:
           'subnet router'";
        leaf id {
          type dhcp:options;
          description "DHCP option to request from, or inform server of.";
        }
        leaf value {
          type string;
          description "Optional value, only used for non-flag request options.
                       Example: option:hostname, value:xyzzy
                                option:clientid, value:01:02:03:04:05:06:07:08:09:0a
                                option:0x51,     value:xyzzy.example.com";
           must "../id != 'hostname' or re-match(., '[a-zA-Z0-9\\-_]{1,64}')";
        }
      }
      leaf route-preference {
        type route-preference;
        default 5;
        description
          "The preference (administrative distance) that all DHCP routes are
           installed with, option 3, 33 and 121.  The default preferfence (5)
           is higher (less worth) than static routes, but lower than those
           learned via dynamic routing protocols, like OSPF.";
      }
    }
  }
}
