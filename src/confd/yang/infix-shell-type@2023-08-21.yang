module infix-shell-type {
  yang-version 1.1;
  namespace "urn:ietf:params:xml:ns:yang:infix-shell-type";
  prefix infixsh;

  organization "KernelKit";
  contact      "kernelkit@googlegroups.com";
  description  "Infix augments and deviations to ietf-system.";

  revision 2023-08-21 {
    description "Initial revision.";
    reference "internal";
  }

  /*
   * Identities
   */

  identity shell-type {
    description "Base identity from which specific shell types are derived.";
  }

  identity bash {
    description "Bourne again shell (BASH), standard UNIX shell.";
    base shell-type;
  }
  identity clish {
    description "Dedicated switch/router shell, similar to Cisco/JunOS.";
    base shell-type;
  }
  identity sh {
    description "POSIX shell, the original plain UNIX shell.";
    base shell-type;
  }
  identity false {
    description "Shell login disabled, both console and SSH.";
    base shell-type;
  }
}
