module infix-keystore {
  yang-version 1.1;
  namespace "urn:infix:keystore:ns:yang:1.0";
  prefix infix-ks;
  import ietf-keystore {
    prefix ks;
  }
  import infix-crypto-types {
    prefix infix-ct;
  }
  revision 2025-02-04 {
    description "Initial";
  }
  deviation "/ks:keystore/ks:asymmetric-keys/ks:asymmetric-key/ks:public-key-format" {
    deviate replace {
      type identityref {
        base infix-ct:public-key-format;
      }
    }
  }
  deviation "/ks:keystore/ks:asymmetric-keys/ks:asymmetric-key/ks:private-key-format" {
    deviate replace {
      type identityref {
        base infix-ct:private-key-format;
      }
    }
  }
}
