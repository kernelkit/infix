module kernelkit-infix-deviations {
    yang-version 1.1;
    namespace "urn:kernelkit:params:xml:ns:yang:infix";
    prefix "kkit";
    import ietf-system {
        prefix sys;
    }
    organization "KernelKit";
    contact "kernelkit@googlegroups.com";
    description "Infix deviations in standard yang models.";

    revision "2023-04-03" {
      description "Initial revision.";
    }

    deviation /sys:system/sys:clock/sys:timezone/sys:timezone-utc-offset/sys:timezone-utc-offset {
      deviate not-supported;
    }
}
