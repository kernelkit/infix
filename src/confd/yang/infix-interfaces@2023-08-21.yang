module infix-interfaces {
  yang-version 1.1;
  namespace "urn:infix:interfaces:ns:yang:1.0";
  prefix infix-if;

  import infix-if-type {
    prefix infixift;
  }
  import ietf-interfaces {
    prefix if;
  }

  include infix-if-base;
  include infix-if-bridge;
  include infix-if-veth;

  organization "KernelKit";
  contact      "kernelkit@googlegroups.com";
  description  "Linux bridge and lag extensions for ietf-interfaces.";

  revision 2023-08-21 {
    description "Move port augment to submodule for infix-if-bridge and
                 infix-if-lag (later) which reference it.

                 Add deviation to if:type to limit the iana-if-types to
                 only those supported, also reduce list for CLI <TAB>.

                 Lint: move include and import to match canonical order.";
    reference "internal";
  }

  revision 2023-06-05 {
    description "Initial revision.";
    reference "internal";
  }

  /*
   * Data Nodes
   */

  deviation "/if:interfaces/if:interface/if:type" {
    deviate replace {
      type identityref {
	base infixift:infix-interface-type;
      }
    }
  }

  deviation "/if:interfaces-state" {
    deviate not-supported;
  }
}
